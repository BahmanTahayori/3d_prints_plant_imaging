# -*- coding: utf-8 -*-
"""
Parametric FreeCAD model for a 4-plant rectangular PET-imaging plant container.

Creates:
  1) Main_Container: one-piece rectangular holder/tray with four top openings,
     one perimeter wall, a closed bottom, internally connected lower wells, internal
     alignment pins, and a hollow central irrigation/distribution column.
  2) Single_Container: one removable insert container design that fits each opening.
  3) Dish: top carrier plate with four basket windows/seats, matching pin holes,
     and a central fill/access hole above the hollow column.
  4) Basket: one removable plant basket design carried by the dish.

Revision v29 — vertical hollow dish handles:
  - Adds a vertical hollow/loop handle style for the dish. The handle is made
    from two upright posts plus a top bridge, leaving an open grip window.
  - The handle can be placed on both X ends as before, but now rises vertically
    above the dish instead of being a flat horizontal tab.
  - The old flat-tab handle remains available with dish_handle_style="flat_tab".

Revision v27 — configurable part-label prefix:
  - Adds part_label_prefix so generated part IDs can be changed from A1-A4
    to C1-C4, B1-B4, R1-R4, etc., without editing label-generation code.
  - Main-container labels, dish labels, single-container labels, basket labels,
    and generated object names now use the same prefix.
  - Stroke text now supports seven-segment-style uppercase letters, so non-A
    prefixes such as C are visible in STL/STEP exports.

Revision v28 — fixed lower main-container wall thickness:
  - Adds main_side_wall_thickness, default 4 mm. This controls the lower
    internal liquid-volume wall thickness without changing the generated outer
    dimensions. The lower internal cavity is shaved from the inside, increasing
    the usable inner volume while preserving the top openings, recesses, dish,
    baskets, single containers, bolt/nut fasteners, and labels.

Revision v26 — explicit bolt/pin position inset parameters:
  - Adds alignment_pin_position_mode and explicit X/Y inset-from-outer-edge
    parameters so the four alignment bolts can be moved farther from the outside
    edges, toward the centre, without indirectly changing wall margins.
  - Keeps v25 bolt-style dish fasteners and printable nuts.

Revision v25 — bolt-style dish fasteners and printable nuts:
  - Converts the four main-container alignment pins into bolt-like vertical
    fasteners when alignment_fastener_style="bolt_and_nut".
  - Dish holes are sized for the bolt/thread outer diameter plus clearance.
  - Adds matching printable hex nuts as separate Part::Feature objects, positioned
    on top of the dish by default.
  - The bolt height can auto-expand so enough thread remains above the dish for
    nut engagement.
  - The bolt thread is represented by printable stacked circular ridges rather
    than a true helical ISO thread, which is more robust for small 3D-printed
    PET container parts.

Revision v23 — recess-aware main-container auto-sizing:
  - The main-container outer length/width now automatically include the full
    single-container flange recess/counterbore footprint.
  - main_opening_side_margin_x/y are now treated as the requested clear solid
    margin OUTSIDE the recess/seat, not merely outside the through-opening.
    Therefore, when the recess grows, the main container grows too.
  - The macro reports both the requested clear margin outside the recess and the
    resulting through-opening-edge-to-outside-wall distance.

Revision v24 — recess-aware main-height fix:
  - effective_main_height() now includes the single-container recess depth when
    auto_expand_main_height_to_single=True. This keeps the inserted single
    container bottom above the closed main-container bottom even when the flange
    sits down inside the top recess.
  - The macro prints the generated main height and single-container bottom
    clearance above the closed bottom.

Revision v22 — recess-depth fix and clearer insert seat:
  - main_single_container_recess_depth is no longer silently clamped to
    single_top_flange_thickness. If the value is too deep for the preserved top
    rib, validation raises a clear error instead of making the model appear
    unchanged.
  - The dish Z placement is protected from dropping below the main-container rim
    when a deep recess is used.
  - The macro prints the effective recess depth so parameter changes are visible.

Revision v21 — explicit opening margins, optional centre column, and insert-seat recess:
  - Adds explicit main_opening_side_margin_x/y parameters; default 10 mm.
    These define the distance from the outermost main openings to the main-container
    outside walls. The effective margin auto-increases only if connector/seat geometry
    requires more material.
  - Adds enable_central_column as a true/false switch for creating the physical
    middle irrigation column. The dish central fill hole can remain present even
    when the physical column is disabled.
  - Adds a shallow top seat/counterbore around each main opening so the removable
    single-container flange rests in a recess/ledge instead of relying only on
    the flat top surface.

Revision v20 — single-module default:
  - Returns the default macro view to one modular Main_Container, one Dish, one
    Single_Container_A1, and one Basket_A1.
  - Preserves all v19 modular changes: no flat-wall centre slots, retained top
    slots, and four edge-open dovetail slots on each side.
  - No modular connector tabs or neighbouring modules are shown by default.
  - The array-preview code remains available and can be re-enabled parametrically.

Revision v19:
  - Removes the horizontal connector slots from the flat side-wall centres.
  - Adds edge-open dovetail slots next to the vertical corner edges: four per side
    (two corner edges x two staggered height levels).
  - Retains the top-inserted slots/tabs. No slots are added to the bottom.
  - Connector tabs are shorter than their slots and include a smaller recessed
    plier head for removal without creating an external bump.
  - Removes the former blind top-bridge locking system; modular connection is now
    provided only by recessed removable top tabs and edge-open connector tabs.
  - Optional preview can generate a modular main-container array for checking
    multi-module layouts and connector-tab positions.
  - Single container, basket, dish openings, and existing mating rules are preserved.

Revision v15:
  - Dish handle tabs can be placed at both X ends of the dish.
  - A1-A4 ID labels are engraved/recessed by default on the main-container,
    dish, single-container, and basket top surfaces so stacked parts sit flat.
  - Label scale defaults to 0.40 for all A1-A4 part labels.
  - Nominal liquid capacities are calculated from the parametric dimensions,
    and recessed 25 mL interval calibration bars plus numeric labels are added
    to side walls where the requested volume level fits below the top exclusion zone.
  - Volume bars/labels are intentionally omitted from the upper 20 mm by default.
  - Default display is simplified: Main_Container, Dish, one Single_Container,
    and one Basket only. The mating-dimensions note is disabled by default.
  - P.main_height is now a minimum height when auto_expand_main_height_to_single=True;
    the generated holder height expands automatically for tall single containers.
  - single_body_length and single_body_width are now the master XY dimensions.
  - Main-container XY size auto-fits both larger and smaller insert dimensions when
    auto_fit_main_outer_xy_to_single=True.
  - Basket lower body can now be derived from the single-container internal cavity,
    while the basket upper lip remains intentionally larger so it can be carried by
    the dish/rim.
  - Uses the user-provided default parameters from 2026-06-03.
  - Basket lower-body fit is now fully parametric: it can follow the global
    fit_clearance_xy or use independent X/Y clearances, with no hard-coded
    16.2 x 6.2 mm basket dimensions.
  - Dish outer footprint can now auto-fit both smaller and larger part layouts;
    when auto_fit_dish_outer_xy_to_layout=True, dish_outer_length/width are no
    longer fixed minimums that prevent the dish from shrinking.
  - Export settings now have safe defaults and maybe_export() uses getattr(),
    so custom parameter blocks copied from older versions do not crash when
    export_step/export_stl/export_dir are absent.

How to use:
  - Open FreeCAD.
  - File -> New.
  - Macro -> Macros... -> Create, paste/run this file; or run with FreeCADCmd.
  - Change the parameters in class P below and re-run.

Units: millimetres.
"""

import math
import os

import FreeCAD as App
import Part

try:
    import FreeCADGui as Gui
except Exception:  # FreeCADCmd/headless
    Gui = None


# -----------------------------------------------------------------------------
# PARAMETERS — edit these in most cases
# -----------------------------------------------------------------------------
class P:
    # General fabrication tolerances
    fit_clearance_xy = 1.25       # one-side clearance for sliding fits, mm
    z_clearance = 0.50            # vertical clearance between stacked parts, mm
    fillet_radius = 0         # set 0 to disable simple all-edge fillets

    # Main container / holder tray.
    # Defaults approximate the uploaded main-container 3MF footprint: 120 x 60 x 56 mm.
    # If auto_expand_main_height_to_single=True, effective_main_height() will expand
    # upward when single_depth is larger than main_height so the insert does not
    # protrude through the closed bottom.
    main_outer_length = 120.0
    main_outer_width = 60.0
    main_height = 56.0
    # True means main_outer_length/main_outer_width are only reference values;
    # the generated main holder shrinks or grows from single_body_length/width.
    # False keeps the old behaviour: these are minimum outer dimensions.
    auto_fit_main_outer_xy_to_single = True
    auto_expand_main_height_to_single = True
    main_bottom_thickness = 2.0   # closed bottom; no cut reaches below this plane
    main_min_wall_thickness = 3.5 # minimum outside perimeter wall; extra space stays as wall

    # Lower main-container side-wall thickness.
    # This controls the wall thickness of the LOWER internal liquid-volume cavity.
    # It is shaved from the inside only: the generated outside dimensions stay
    # unchanged, while the inner liquid volume expands/contracts to leave this
    # wall thickness. The top openings, flange recesses, dish, baskets, and
    # single-container dimensions are not changed by this parameter.
    main_side_wall_thickness = 3.5

    # Explicit clear solid margin OUTSIDE the single-container flange recess/seat.
    # These values are measured from the outer edge of the recess/counterbore to
    # the outside wall of the main container. The through-opening edge-to-wall
    # distance is therefore:
    #   main_opening_side_margin + recess_overhang
    # The generated main holder auto-expands if the recess, slots, pins, or minimum
    # land require more material.
    main_opening_side_margin_x = 12.0
    main_opening_side_margin_y = 12.0

    # Optional top seat/counterbore around each main opening. The through-opening
    # remains sized for the single-container body; this shallow larger recess
    # catches the single-container top flange so the insert cannot fall into the
    # main container.
    enable_main_single_container_recess = True
    main_single_container_recess_depth = 1.80  # visible counterbore depth; v22 does not silently clamp this
    main_single_container_recess_clearance_xy = 0.6
    main_single_container_recess_min_land = 1.00

    # Four top openings. By default these are derived from the single-container body.
    # With the defaults below, each opening is single_body + 2*fit_clearance_xy.
    opening_gap_x = 21             # top bridge/rib between left/right openings
    opening_gap_y = 21            # top bridge/rib between lower/upper openings

    # Internally connect the four wells below the upper bridge/rib while preserving
    # four separate top openings and a closed bottom.
    connect_main_wells_internally = True
    main_top_bridge_height = 4.0      # top divider material preserved from the top downward
    main_connection_overlap = .70    # overlap into neighbouring wells for robust boolean cuts

    # Single removable container body. Main opening = body + 2*fit_clearance_xy.
    # If you want to use the earlier larger inserts, increase these two dimensions;
    # the main tray will auto-expand only if needed for wall thickness and height.
    # Stress-test defaults requested by user. Change these two values and the
    # main openings, main outer XY, dish windows, basket body/lip, and dish size
    # will all update from them.
    single_body_length = 33.0
    single_body_width = 23.0
    single_depth = 160.0
    single_wall = 1.50
    single_bottom = 2.00
    single_top_flange_overhang = 2.00
    single_top_flange_thickness = 1.6
    single_corner_fillet = 0.0

    # Dish/top carrier plate
    dish_outer_length = 124.0
    dish_outer_width = 64.0
    auto_expand_dish_to_main = True
    # True means dish_outer_length/dish_outer_width are only manual fallback/reference
    # values. The generated dish plate shrinks or grows from the main holder and
    # basket-lip layout. False keeps the older behaviour where dish_outer_length/width
    # act as minimum dimensions.
    auto_fit_dish_outer_xy_to_layout = True
    dish_outer_overhang = 0.0
    dish_min_edge_margin = 2.0     # minimum dish material outside window/recess features, mm
    dish_thickness = 3
    dish_basket_lip_recess_depth = 1.6
    dish_basket_lip_recess_clearance = 1.2
    # Central dish opening.
    # v33: the old circular centre fill hole is disabled and replaced by a
    # square central through-opening plus a shallow top recess/counterbore.
    enable_dish_central_fill_hole = False
    dish_central_fill_hole_diameter = 4.0  # legacy round hole diameter; ignored when square opening is enabled

    use_square_dish_central_opening = True
    dish_central_square_opening_length = 14.0
    dish_central_square_opening_width = 14.0
    enable_dish_central_square_recess = True
    dish_central_square_recess_side_clearance = 0.75  # recess is 0.5 mm larger on each side
    dish_central_square_recess_depth = 1.0           # recess depth into top of dish

    # v36 simple acrylic U-clip trial on ONE long side of ONE dish opening.
    # The older full-perimeter acrylic guide/U-channel experiments are disabled.
    # This version adds only two short U-shaped clips, each 10 mm long, fused
    # directly to the dish. The dish itself acts as the bottom of the U; the two
    # raised side walls leave an internal gap for a 2 mm acrylic sheet.
    enable_acrylic_u_channels = False          # disable older full-perimeter v35 U-channels
    enable_acrylic_window_guides = False       # disable older v34 rail/groove trial
    show_acrylic_u_sheet_preview = False

    enable_simple_acrylic_u_clips = True
    simple_acrylic_u_clip_opening_index = 1    # 1=lower-left, 2=lower-right, 3=upper-left, 4=upper-right
    simple_acrylic_u_clip_side = "outer_long_side"
    simple_acrylic_u_clip_count = 2
    simple_acrylic_u_clip_length = 10.0        # each U clip length, mm
    simple_acrylic_u_clip_offset_from_center = 0.0  # 0 = auto-place clips symmetrically along the long side

    acrylic_sheet_thickness = 2.0              # reference sheet thickness, mm
    simple_acrylic_u_clip_inner_gap = 2.1      # empty internal U gap; use 2.1-2.2 mm for 2 mm acrylic
    simple_acrylic_u_clip_wall_thickness = 2.0
    simple_acrylic_u_clip_height = 14.0         # height above dish top, mm
    simple_acrylic_u_clip_base_groove_depth = 0.0
    simple_acrylic_u_clip_clearance_from_basket_recess = 3.0

    # v37: one bolt/screw hole through each U-clip.
    # The hole runs across the U gap, through both clip walls and the acrylic sheet.
    simple_acrylic_u_clip_add_bolt_holes = True
    simple_acrylic_u_clip_bolt_hole_diameter = 4      # e.g. M2 clearance; adjust for your screw
    simple_acrylic_u_clip_bolt_hole_height_above_dish = 10.0  # centre of hole above dish top, mm
    simple_acrylic_u_clip_bolt_hole_x_offset = 0.0      # 0 = centred along each 10 mm U-clip
    simple_acrylic_u_clip_bolt_hole_extra_length = 2.0  # cutter margin beyond U walls, mm

    # v38: symmetric acrylic U-clips around all four dish openings.
    # These use the SAME U dimensions above: 10 mm length, 2.1 mm gap,
    # 2 mm wall, 14 mm height, and the same bolt-hole settings.
    # Clips are fused into the dish; no separate acrylic/clip parts are created.
    enable_symmetric_acrylic_u_clips = True
    symmetric_acrylic_u_clip_opening_indices = (1, 2, 3, 4)
    symmetric_acrylic_u_clip_sides = ("N", "S", "E", "W")  # all sides of each selected opening
    symmetric_acrylic_u_clip_count_long_side = 2   # N/S sides; clips run along X
    symmetric_acrylic_u_clip_count_short_side = 2  # E/W sides; clips run along Y
    # v39: when two openings share the same strip/rib between them, create only
    # ONE shared pair of U clips in that strip, not two pairs from both openings.
    symmetric_acrylic_u_clip_share_internal_sides = True
    symmetric_acrylic_u_clip_internal_side_count = 2
    symmetric_acrylic_u_clip_long_side_offset_from_center = 0.0   # 0 = auto-symmetric
    symmetric_acrylic_u_clip_short_side_offset_from_center = 0.0  # 0 = auto-symmetric

    # Basket: lower body passes through dish window; top lip rests on dish and is carried by it.
    # By default, basket footprint follows the single-container body, so one change
    # updates the single insert, main opening, basket, and dish window together.
    derive_basket_from_single = True
    # True = basket lower body is derived from the SINGLE-CONTAINER INTERNAL CAVITY,
    # so it can drop/sit into the single container. The basket upper lip remains
    # intentionally larger via basket_lip_overhang_x/y.
    # False = older behaviour, where basket lower body was derived from the
    # single-container OUTER body using basket_body_length/width_allowance.
    basket_lower_body_fits_inside_single = True
    # Basket lower-body clearance is parametric.
    # True: use the global sliding-fit clearance P.fit_clearance_xy for both X and Y.
    # False: use the independent basket_to_single_inner_clearance_x/y values below.
    basket_clearance_follows_fit_clearance = True
    basket_to_single_inner_clearance_x = 0.40  # one-side clearance if basket_clearance_follows_fit_clearance=False
    basket_to_single_inner_clearance_y = 0.40  # one-side clearance if basket_clearance_follows_fit_clearance=False
    basket_min_body_dimension = 0.50
    basket_body_length = 49.0      # used only if derive_basket_from_single=False
    basket_body_width = 18.5       # used only if derive_basket_from_single=False
    basket_body_length_allowance = 3.30  # effective basket length = single_body_length - this
    basket_body_width_allowance = 1.80   # effective basket width  = single_body_width  - this
    # Basket defaults are restored to the earlier shallow-basket design.
    basket_depth = 12.0
    auto_expand_basket_depth_to_bottom = False  # old basket behaviour; helpers still prevent invalid geometry
    basket_min_open_depth = 2.0
    basket_wall = 1.00
    basket_bottom = 1.0
    basket_lip_length = 56.0       # used only if derive_basket_from_single=False
    basket_lip_width = 25.0        # used only if derive_basket_from_single=False
    basket_lip_overhang_x = 4.5  # each side; used when derive_basket_from_single=True
    basket_lip_overhang_y = 4.5   # each side; used when derive_basket_from_single=True
    basket_lip_thickness = 1.4
    basket_corner_fillet = 0.9

    # Basket perforations/slots
    basket_bottom_slot_length = 4.0
    basket_bottom_slot_width = 3.0
    basket_bottom_slot_pitch_x = 5.0
    basket_bottom_slot_pitch_y = 4.0
    basket_side_slot_length = .01
    basket_side_slot_height = .01
    basket_side_slot_pitch = 20.0
    basket_side_slot_z = 3

    # Alignment pins only. Pins are inside the main footprint, placed on solid
    # perimeter/rib material outside the single-container openings. Matching holes
    # are cut into the dish. No external main-container lugs are added.
    enable_alignment_pins = False
    alignment_pin_count = 4            # 2 = front/back internal pins; 4 also adds left/right internal pins
    alignment_pin_diameter = 2.5
    alignment_pin_height = 8
    alignment_pin_hole_clearance = 1
    alignment_pin_min_surround = 0.80  # minimum solid material around each pin within the perimeter strip

    # Explicit alignment fastener positioning.
    # "strip_center" keeps the older behaviour: pins/bolts are placed halfway
    # across the available perimeter strip.
    # "inset_from_outer_edge" places them a user-controlled distance from the
    # outside wall. Increasing the inset moves the fasteners farther from the
    # outer edge and closer to the centre/opening group.
    alignment_pin_position_mode = "inset_from_outer_edge"
    alignment_pin_inset_from_outer_edge_x = 12  # used for left/right bolts, mm
    alignment_pin_inset_from_outer_edge_y = 12  # used for front/back bolts, mm

    # Bolt/nut conversion for the alignment pins. The same four alignment positions
    # are used, but the vertical posts on the main container become bolt-like posts
    # and separate printable nuts are generated above the dish.
    # "pin" keeps the previous smooth-pin behaviour.
    # "bolt_and_nut" uses a smooth core plus printable circular thread ridges.
    alignment_fastener_style = "bolt_and_nut"
    alignment_bolt_auto_height = True
    alignment_bolt_min_thread_above_dish = 3.4  # mm of bolt above dish top for nut engagement
    alignment_bolt_core_diameter = 2.5          # nominal/smooth core diameter, mm
    alignment_bolt_thread_outer_diameter = 3.1  # outside diameter of printed thread ridges, mm
    alignment_bolt_thread_pitch = 1.2           # spacing between circular ridges, mm
    alignment_bolt_thread_ridge_height = 0.30   # axial height of each ridge, mm
    alignment_bolt_unthreaded_base_height = 1.0
    alignment_bolt_tip_clearance = 0.35

    # Matching printable nut. The bore auto-follows the bolt outer diameter unless
    # alignment_nut_bore_diameter is set > 0. This is a clearance nut for printing;
    # the visual/functional grip comes from the bolt ridges and friction, not an
    # exact helical machine thread.
    show_alignment_nuts_in_assembly = True
    alignment_nut_across_flats = 7.5
    alignment_nut_thickness = 3.2
    alignment_nut_bore_diameter = 0.0           # 0 = auto
    alignment_nut_bore_clearance = 0.45
    alignment_nut_bottom_clearance = 0.15
    alignment_nut_corner_fillet = 0.15

    # Dish handle: tabs on the dish only. They are not part of the main box.
    enable_dish_handle = True
    dish_handle_both_ends = True
    dish_handle_length = 20.0
    dish_handle_width = 20.0
    dish_handle_overlap = 0.0
    # Dish handle style. "flat_tab" keeps the old horizontal end tabs.
    # "vertical_hollow" creates an upright handle/loop with an open central grip.
    dish_handle_style = "vertical_hollow"
    dish_vertical_handle_height = 25.0       # vertical rise above dish top, mm
    dish_vertical_handle_wall = 3.0         # Y-post width and top-bridge height, mm
    dish_vertical_handle_thickness_x = 3.0  # front/back thickness of the handle frame, mm
    dish_vertical_handle_inset_from_end = 0.0  # keeps upright handle inside the dish footprint, mm
    dish_vertical_handle_base_penetration = 0.20  # slight overlap into dish for robust fuse, mm

    # Parametric-box-style modular main-container connector system.
    # All modules are identical/genderless. Curved dovetail slots are NARROW at
    # the outside face and WIDER deeper in the wall. Separate double-sided tabs
    # bridge two opposing slots. No connector feature is added to the bottom.
    enable_modular_side_slots = True
    modular_slot_sides = ("N", "S", "E", "W")
    modular_slot_depth = 2.0             # blind depth into each outside wall
    modular_slot_min_back_wall = 1.2     # sealed printable wall behind every slot
    modular_key_clearance = 0.25         # width/height clearance between tab and slot
    modular_fit_clearance_depth_per_side = 0.12
    modular_module_gap = 1.0             # gap between adjacent modules; tab bridges it
    modular_curve_steps = 11
    modular_curve_power = 1.4
    modular_boolean_eps = .2

    # Vertical slots descending from the TOP edge of every side wall. These tabs
    # are inserted vertically from above. Two slots per side avoid the existing
    # central dish-alignment pins and provide stronger anti-separation locking.
    enable_modular_top_vertical_slots = True
    modular_top_slots_per_side = 2
    modular_top_slot_offset_fraction = 0.26
    modular_top_slot_face_width = 7.0
    modular_top_slot_deep_width = 12.0
    modular_top_slot_vertical_length = 24.0
    modular_top_tab_length_clearance = 4.0
    modular_top_tab_surface_recess = 0.8

    # V18 flat-wall horizontal slots are disabled in v19. They were visually
    # intrusive and are replaced by edge-open slots near the vertical corners.
    enable_modular_side_horizontal_slots = False
    modular_side_slot_face_height = 6.0       # legacy compatibility only
    modular_side_slot_deep_height = 9.0       # legacy compatibility only
    modular_side_slot_horizontal_length = 30.0  # legacy compatibility only
    modular_side_slot_z_fraction = 0.64       # legacy compatibility only
    modular_side_tab_length_clearance = 6.0   # legacy compatibility only

    # Edge-open connector slots. Each side has four slots total:
    # two vertical corner edges x two height levels. The slot opens to the corner
    # edge, so the shorter connector tab can slide in from the edge and can later
    # be gripped with pliers. North/south and east/west levels are staggered to
    # prevent perpendicular connector tabs colliding at a shared module corner.
    enable_modular_edge_slots = True
    modular_edge_slots_per_vertical_edge = 2  # 2 per edge => 4 on each side
    modular_edge_slot_z_fractions_ns = (0.30, 0.62)
    modular_edge_slot_z_fractions_ew = (0.44, 0.76)
    modular_edge_slot_insertion_length = 20.0  # distance from corner edge into side face
    modular_edge_slot_face_height = 12.0       # narrow outside throat height
    modular_edge_slot_deep_height = 16.0       # wider internal dovetail height
    modular_edge_tab_length_clearance = 3.5    # unused edge space for plier access
    modular_edge_tab_head_length = 2.0         # smaller grip within unused slot length
    modular_edge_tab_head_height_fraction = 0.48

    # Smaller-than-body recessed plier grip. The grip never extends above the top
    # surface or outside the side envelope. It is intended for needle-nose pliers.
    modular_tab_head_width_fraction = 0.48
    modular_tab_head_length = 3.0
    modular_tab_head_height = 2.0
    modular_tab_head_gap_depth = 0.8
    modular_tab_edge_fillet = 0.35

    # Compatibility aliases used by the shared validation/wall-sizing code. The
    # legacy shared validation uses these aliases; v19 geometry uses the detailed top/edge parameters above.
    modular_slot_length_x = modular_side_slot_horizontal_length
    modular_slot_length_y = modular_side_slot_horizontal_length
    modular_slot_height = modular_side_slot_face_height
    modular_slot_z_center = 18.0

    # v17 blind top bridges/sockets are intentionally disabled.
    enable_modular_top_locks = False
    modular_lock_sides = ()
    enable_modular_central_cross_lock = False

    # Single-module display is the default. It shows one modular Main_Container,
    # one Dish, one Single_Container_A1, and one Basket_A1. The main container still
    # contains all top and vertical-edge modular slots. No neighbour modules or
    # connector-tab sets are displayed unless the array preview is enabled below.
    show_modular_array_preview = False

    # Optional future array preview. Set show_modular_array_preview=True and change
    # these counts when you want to inspect how several identical modules connect.
    modular_array_count_x = 2
    modular_array_count_y = 2
    modular_preview_show_connector_keys = True
    modular_preview_show_top_lock_bridges = False
    modular_preview_show_central_cross_lock = False
    modular_preview_show_dishes = False
    modular_preview_show_inserts = False
    modular_preview_show_baskets = False
    modular_preview_show_reference_parts = True

    # Part ID labels. These are made from simple stroke geometry, not font files,
    # so they should export with STL/STEP without a FreeCAD font dependency.
    # Default is engraved/recessed, not raised, so stacked parts sit flat.
    # Change this to "C" for C1-C4, "B" for B1-B4, etc.
    part_label_prefix = "C - "
    enable_part_labels = False
    label_style = "engraved"        # "engraved" or "raised"
    label_depth = 2              # cut depth for engraved labels, mm
    label_raised_height = 0.30      # extrusion height if label_style="raised", mm
    label_stroke_width = 0.2
    # Small default labels fit on narrow top frame/flange strips.
    main_label_scale = 0.40
    single_label_scale = 0.40
    basket_label_scale = 0.4
    dish_label_scale = 0.40

    # Volume/capacity marks. 1 mL = 1000 mm^3. Marks are nominal geometric
    # estimates, not calibrated metrology after slicer/extrusion effects.
    enable_volume_bars = False
    volume_bar_interval_ml = 25
    volume_bar_major_every_ml = 50
    volume_bar_length_minor = 5.0
    volume_bar_length_major = 8.0
    volume_bar_thickness_z = 0.45
    volume_bar_projection = 0.35    # used only if volume_mark_style="raised"
    volume_mark_style = "engraved"  # "engraved" avoids protrusions on fitting surfaces
    volume_mark_depth = 0.30        # side-wall cut depth for engraved volume marks, mm
    volume_label_every_ml = 25      # numeric side labels; set 0 to disable
    volume_mark_top_exclusion_mm = 20.0  # no volume bars/labels in the top 20 mm safety zone
    volume_label_scale = 0.40
    volume_label_stroke_width = 0.28

    # Central hollow irrigation/distribution column at the junction of the four openings.
    # Set enable_central_column=False to remove the physical middle column from the
    # main container. The dish centre fill hole is controlled separately above.
    enable_central_column = False
    central_column_diameter = 6.0
    central_column_clearance_to_openings = 0.30  # effective opening gaps grow if required
    central_column_cutout_clearance = 0.20       # remove square junction material above bottom, then add column
    central_column_bore_diameter = 2.6           # vertical blind top-fill bore
    central_column_bore_bottom_z = 4.0           # bore stops here; must be above bottom, so bottom stays closed
    central_column_port_diameter = 1.2           # horizontal liquid-distribution ports
    central_column_port_levels = 5               # equally spaced along height
    central_column_port_min_z = 8.0
    central_column_port_max_z = 44.0

    # What to build/display. Default macro view is intentionally simple:
    # Main_Container, Dish, one Single_Container_A1, and one Basket_A1.
    add_four_insert_copies = False
    add_four_basket_copies = True
    add_reference_parts_to_side = False
    create_mating_dimensions_note = False

    # Optional export settings. These are disabled by default so running as a
    # FreeCAD macro only creates/shows the model. Enable only when needed.
    export_step = False
    export_stl = False
    export_dir = os.path.join(os.path.expanduser("~"), "PET_plant_container_exports")
    export_visible_only = False


def part_label_prefix():
    """User-facing prefix for A1-A4 style part IDs.

    Examples:
      part_label_prefix = "A" -> A1, A2, A3, A4
      part_label_prefix = "C" -> C1, C2, C3, C4
    """
    prefix = str(getattr(P, "part_label_prefix", "A")).strip()
    return prefix if prefix else "A"


def part_label(index):
    """Return the visible part label for a 1-based opening index."""
    return f"{part_label_prefix()}{int(index)}"


def safe_name_fragment(value):
    """Make a label safe for a FreeCAD object name."""
    out = []
    for ch in str(value):
        out.append(ch if ch.isalnum() else "_")
    cleaned = "".join(out).strip("_")
    return cleaned or "Label"


def part_label_name(index):
    """FreeCAD-object-name-safe version of part_label(index)."""
    return safe_name_fragment(part_label(index))

def main_opening_length():
    return P.single_body_length + 2.0 * P.fit_clearance_xy


def main_opening_width():
    return P.single_body_width + 2.0 * P.fit_clearance_xy


def physical_central_column_enabled():
    return bool(getattr(P, "enable_central_column", True))


def dish_central_fill_hole_enabled():
    return bool(getattr(P, "enable_dish_central_fill_hole", True))


def effective_opening_gap_x():
    if physical_central_column_enabled():
        return max(P.opening_gap_x,
                   P.central_column_diameter + 2.0 * P.central_column_clearance_to_openings)
    return P.opening_gap_x


def effective_opening_gap_y():
    if physical_central_column_enabled():
        return max(P.opening_gap_y,
                   P.central_column_diameter + 2.0 * P.central_column_clearance_to_openings)
    return P.opening_gap_y


def _small_dimension_wall(requested_wall, length, width, fraction=0.30, min_wall=0.05):
    """Return a wall thickness that cannot make the inside box negative.

    This is mainly a geometry-safety helper. A 1 mm wide stress-test insert is
    not a practical printable container with 1.5 mm walls, but the macro should
    still regenerate cleanly and show that all dependent dimensions are linked.
    """
    min_dim = max(min(float(length), float(width)), 0.10)
    return max(min_wall, min(float(requested_wall), min_dim * fraction))


def effective_single_wall():
    return _small_dimension_wall(P.single_wall, P.single_body_length, P.single_body_width, fraction=0.30)


def effective_single_bottom():
    return min(float(P.single_bottom), max(0.10, float(P.single_depth) - 0.50))


def _scaled_allowance(dim, allowance, max_fraction=0.25):
    """Limit basket allowance so very small inserts do not produce negative baskets."""
    dim = max(float(dim), 0.10)
    return min(float(allowance), dim * max_fraction)


def main_bay_length():
    """Overall span of the 2 x 2 opening group, including the top bridges."""
    return 2.0 * main_opening_length() + effective_opening_gap_x()


def main_bay_width():
    """Overall span of the 2 x 2 opening group, including the top bridges."""
    return 2.0 * main_opening_width() + effective_opening_gap_y()


def main_side_wall_thickness():
    """Lower internal side-wall thickness of the main container.

    This is an inside-only change: effective_main_outer_length()/width() are not
    altered by this value. The lower liquid-volume cavity is expanded inward from
    the outer walls until this wall thickness remains.
    """
    return max(0.05, float(getattr(P, "main_side_wall_thickness", P.main_min_wall_thickness)))


def main_lower_cavity_length():
    return max(0.10, effective_main_outer_length() - 2.0 * main_side_wall_thickness())


def main_lower_cavity_width():
    return max(0.10, effective_main_outer_width() - 2.0 * main_side_wall_thickness())


def main_lower_cavity_height():
    return max(0.0, effective_main_height() - P.main_bottom_thickness - P.main_top_bridge_height)


def single_container_recess_enabled():
    return bool(getattr(P, "enable_main_single_container_recess", True))


def main_single_container_recess_clearance_xy():
    return max(0.0, float(getattr(P, "main_single_container_recess_clearance_xy", 0.30)))


def main_single_container_recess_depth():
    """Depth of the shallow flange seat/counterbore in the main container.

    v21 silently clamped this to single_top_flange_thickness. That made larger
    user values appear to do nothing. In v22 the requested value is returned
    directly and validate_parameters() gives a clear error only if it is too
    deep for the preserved top rib/bridge geometry.
    """
    if not single_container_recess_enabled():
        return 0.0
    return max(0.0, float(getattr(P, "main_single_container_recess_depth", 0.0)))


def main_single_container_recess_length():
    return single_flange_length() + 2.0 * main_single_container_recess_clearance_xy()


def main_single_container_recess_width():
    return single_flange_width() + 2.0 * main_single_container_recess_clearance_xy()


def main_single_container_recess_overhang_x():
    if not single_container_recess_enabled():
        return 0.0
    return max(0.0, (main_single_container_recess_length() - main_opening_length()) / 2.0)


def main_single_container_recess_overhang_y():
    if not single_container_recess_enabled():
        return 0.0
    return max(0.0, (main_single_container_recess_width() - main_opening_width()) / 2.0)


def main_recess_min_land():
    return max(0.0, float(getattr(P, "main_single_container_recess_min_land", 1.0)))


def requested_clear_margin_outside_recess_x():
    """Requested solid material outside the flange recess on left/right sides."""
    return max(0.0, float(getattr(P, "main_opening_side_margin_x", P.main_min_wall_thickness)))


def requested_clear_margin_outside_recess_y():
    """Requested solid material outside the flange recess on front/back sides."""
    return max(0.0, float(getattr(P, "main_opening_side_margin_y", P.main_min_wall_thickness)))


def required_seat_margin_x():
    """Minimum through-opening-edge-to-wall margin required by the flange recess."""
    return main_single_container_recess_overhang_x() + main_recess_min_land()


def required_seat_margin_y():
    """Minimum through-opening-edge-to-wall margin required by the flange recess."""
    return main_single_container_recess_overhang_y() + main_recess_min_land()


def requested_recess_aware_margin_from_opening_x():
    """Requested through-opening-edge-to-wall margin after adding the recess footprint.

    The user-facing main_opening_side_margin_x is measured outside the recess, so
    the main holder must add the recess overhang to get the actual distance from
    the through-opening edge to the outside wall.
    """
    return requested_clear_margin_outside_recess_x() + main_single_container_recess_overhang_x()


def requested_recess_aware_margin_from_opening_y():
    """Requested through-opening-edge-to-wall margin after adding the recess footprint."""
    return requested_clear_margin_outside_recess_y() + main_single_container_recess_overhang_y()


def effective_main_opening_side_margin_x():
    """Actual distance from the through-opening edge to the outside wall in X."""
    return max(requested_recess_aware_margin_from_opening_x(),
               required_main_wall_strip_x(),
               required_seat_margin_x())


def effective_main_opening_side_margin_y():
    """Actual distance from the through-opening edge to the outside wall in Y."""
    return max(requested_recess_aware_margin_from_opening_y(),
               required_main_wall_strip_y(),
               required_seat_margin_y())


def effective_clear_margin_outside_recess_x():
    """Actual remaining clear solid material outside the flange recess in X."""
    return max(0.0, effective_main_opening_side_margin_x() - main_single_container_recess_overhang_x())


def effective_clear_margin_outside_recess_y():
    """Actual remaining clear solid material outside the flange recess in Y."""
    return max(0.0, effective_main_opening_side_margin_y() - main_single_container_recess_overhang_y())


def main_insert_z():
    """Assembly Z position for single-container body when flange sits in the main recess."""
    return effective_main_height() - P.single_depth - main_single_container_recess_depth()


def assembled_single_container_top_z():
    return main_insert_z() + P.single_depth + P.single_top_flange_thickness


def main_dish_support_z():
    """Z level used to place the dish.

    Normally the dish follows the top of the inserted single-container flange.
    If a user sets the main recess deeper than the flange thickness, the flange
    top drops below the main-container rim; in that case the dish must not drop
    into the main rim, so use the higher of the two support levels.
    """
    return max(effective_main_height(), assembled_single_container_top_z())



def alignment_bolt_and_nut_enabled():
    return str(getattr(P, "alignment_fastener_style", "pin")).strip().lower() in {
        "bolt", "bolts", "bolt_and_nut", "bolt-nut", "bolt_nut"
    }


def alignment_bolt_core_diameter():
    if alignment_bolt_and_nut_enabled():
        return max(0.2, float(getattr(P, "alignment_bolt_core_diameter", P.alignment_pin_diameter)))
    return float(P.alignment_pin_diameter)


def alignment_fastener_outer_diameter():
    if alignment_bolt_and_nut_enabled():
        return max(
            alignment_bolt_core_diameter(),
            float(getattr(P, "alignment_bolt_thread_outer_diameter", P.alignment_pin_diameter)),
        )
    return float(P.alignment_pin_diameter)


def alignment_fastener_hole_diameter():
    """Diameter of the dish clearance hole for the alignment bolt/pin."""
    return alignment_fastener_outer_diameter() + max(0.0, float(P.alignment_pin_hole_clearance))


def effective_alignment_fastener_height():
    """Height of the post rising from the main-container top.

    In bolt/nut mode this can auto-grow so the bolt reaches through the dish and
    still leaves enough thread for a nut above the dish.
    """
    h = float(P.alignment_pin_height)
    if alignment_bolt_and_nut_enabled() and bool(getattr(P, "alignment_bolt_auto_height", True)):
        dish_z = main_dish_support_z() + float(P.z_clearance)
        needed = (
            (dish_z + float(P.dish_thickness) - effective_main_height())
            + float(getattr(P, "alignment_bolt_min_thread_above_dish", 3.0))
        )
        h = max(h, needed)
    return h


def alignment_nut_bore_diameter():
    manual = float(getattr(P, "alignment_nut_bore_diameter", 0.0))
    if manual > 0:
        return manual
    return alignment_fastener_outer_diameter() + max(0.0, float(getattr(P, "alignment_nut_bore_clearance", 0.4)))


def alignment_nut_assembly_z(dish_z):
    return float(dish_z) + float(P.dish_thickness) + max(0.0, float(getattr(P, "alignment_nut_bottom_clearance", 0.0)))

def internal_pin_required_wall_strip():
    if not P.enable_alignment_pins:
        return P.main_min_wall_thickness
    return max(P.main_min_wall_thickness,
               alignment_fastener_outer_diameter() + 2.0 * P.alignment_pin_min_surround)


def _normalise_modular_slot_sides():
    sides = getattr(P, "modular_slot_sides", ("N", "S", "E", "W"))
    if isinstance(sides, str):
        # Accept strings such as "NSEW" or "N,S,E,W".
        sides = sides.replace(",", " ").split() if "," in sides or " " in sides else list(sides)
    return {str(side).strip().upper() for side in sides if str(side).strip()}


def modular_slots_enabled():
    return bool(getattr(P, "enable_modular_side_slots", False))


def modular_top_locks_enabled():
    return bool(getattr(P, "enable_modular_top_locks", False))


def _normalise_modular_lock_sides():
    sides = getattr(P, "modular_lock_sides", ("N", "S", "E", "W"))
    if isinstance(sides, str):
        sides = sides.replace(",", " ").split() if "," in sides or " " in sides else list(sides)
    return {str(side).strip().upper() for side in sides if str(side).strip()}


def modular_lock_required_wall_strip():
    if not modular_top_locks_enabled():
        return float(P.main_min_wall_thickness)
    required = (float(P.modular_lock_pin_inset_from_outer_edge) +
                (float(P.modular_lock_pin_diameter) + float(P.modular_lock_pin_clearance)) / 2.0 +
                max(0.6, float(P.modular_lock_pin_min_end_margin) * 0.25))
    return max(float(P.main_min_wall_thickness), required)


def modular_slot_required_wall_strip():
    if not modular_slots_enabled():
        return float(P.main_min_wall_thickness)
    return max(float(P.main_min_wall_thickness),
               float(P.modular_slot_depth) + float(P.modular_slot_min_back_wall))


def required_main_wall_strip_x():
    """Required left/right wall strip before the opening group.

    X-side strip must support E/W modular slots. Four-pin mode also needs room
    for left/right internal alignment pins.
    """
    req = float(P.main_min_wall_thickness)
    if int(P.alignment_pin_count) >= 4:
        req = max(req, internal_pin_required_wall_strip())
    if modular_slots_enabled() and ({"E", "W"} & _normalise_modular_slot_sides()):
        req = max(req, modular_slot_required_wall_strip())
    if modular_top_locks_enabled() and ({"E", "W"} & _normalise_modular_lock_sides()):
        req = max(req, modular_lock_required_wall_strip())
    return req


def required_main_wall_strip_y():
    """Required front/back wall strip before the opening group.

    Y-side strip must support N/S modular slots and the default front/back
    internal alignment pins.
    """
    req = float(P.main_min_wall_thickness)
    if P.enable_alignment_pins:
        req = max(req, internal_pin_required_wall_strip())
    if modular_slots_enabled() and ({"N", "S"} & _normalise_modular_slot_sides()):
        req = max(req, modular_slot_required_wall_strip())
    if modular_top_locks_enabled() and ({"N", "S"} & _normalise_modular_lock_sides()):
        req = max(req, modular_lock_required_wall_strip())
    return req


def effective_main_outer_length():
    needed = main_bay_length() + 2.0 * effective_main_opening_side_margin_x()
    if getattr(P, "auto_fit_main_outer_xy_to_single", True):
        return needed
    return max(P.main_outer_length, needed)


def effective_main_outer_width():
    needed = main_bay_width() + 2.0 * effective_main_opening_side_margin_y()
    if getattr(P, "auto_fit_main_outer_xy_to_single", True):
        return needed
    return max(P.main_outer_width, needed)


def dish_feature_group_length():
    """Minimum X span needed by basket windows/lip recesses on the dish."""
    feature_len = max(dish_window_length(),
                      effective_basket_lip_length() + float(P.dish_basket_lip_recess_clearance))
    return main_opening_length() + effective_opening_gap_x() + feature_len


def dish_feature_group_width():
    """Minimum Y span needed by basket windows/lip recesses on the dish."""
    feature_wid = max(dish_window_width(),
                      effective_basket_lip_width() + float(P.dish_basket_lip_recess_clearance))
    return main_opening_width() + effective_opening_gap_y() + feature_wid


def required_dish_outer_length_from_layout():
    """Dish length derived from the generated holder and basket-seat layout."""
    required_by_main = effective_main_outer_length() + 2.0 * float(P.dish_outer_overhang)
    required_by_features = dish_feature_group_length() + 2.0 * float(P.dish_min_edge_margin)
    return max(required_by_main, required_by_features)


def required_dish_outer_width_from_layout():
    """Dish width derived from the generated holder and basket-seat layout."""
    required_by_main = effective_main_outer_width() + 2.0 * float(P.dish_outer_overhang)
    required_by_features = dish_feature_group_width() + 2.0 * float(P.dish_min_edge_margin)
    # Handles are separate tabs on the X ends, but the plate should still be wide
    # enough to support their requested width. This does not make external lugs on
    # the main holder.
    if getattr(P, "enable_dish_handle", False):
        required_by_features = max(required_by_features, float(P.dish_handle_width))
    return max(required_by_main, required_by_features)


def effective_dish_outer_length():
    if P.auto_expand_dish_to_main:
        required = required_dish_outer_length_from_layout()
        if getattr(P, "auto_fit_dish_outer_xy_to_layout", True):
            return required
        return max(float(P.dish_outer_length), required)
    return float(P.dish_outer_length)


def effective_dish_outer_width():
    if P.auto_expand_dish_to_main:
        required = required_dish_outer_width_from_layout()
        if getattr(P, "auto_fit_dish_outer_xy_to_layout", True):
            return required
        return max(float(P.dish_outer_width), required)
    return float(P.dish_outer_width)


def single_inner_length():
    """Nominal clear inside length of one removable single container."""
    return max(0.0, float(P.single_body_length) - 2.0 * effective_single_wall())


def single_inner_width():
    """Nominal clear inside width of one removable single container."""
    return max(0.0, float(P.single_body_width) - 2.0 * effective_single_wall())


def basket_to_single_clearance_x():
    """One-side X clearance between basket lower body and single-container inner wall."""
    if getattr(P, "basket_clearance_follows_fit_clearance", True):
        return max(0.0, float(P.fit_clearance_xy))
    return max(0.0, float(P.basket_to_single_inner_clearance_x))


def basket_to_single_clearance_y():
    """One-side Y clearance between basket lower body and single-container inner wall."""
    if getattr(P, "basket_clearance_follows_fit_clearance", True):
        return max(0.0, float(P.fit_clearance_xy))
    return max(0.0, float(P.basket_to_single_inner_clearance_y))


def effective_basket_body_length():
    if P.derive_basket_from_single:
        if getattr(P, "basket_lower_body_fits_inside_single", True):
            # Parametric lower-body rule:
            # basket lower length = single-container inside length - 2*clearance_x.
            # This keeps the lower basket inside the insert while allowing the
            # upper basket lip to remain intentionally larger.
            return max(float(P.basket_min_body_dimension),
                       single_inner_length() - 2.0 * basket_to_single_clearance_x())
        return max(float(P.basket_min_body_dimension),
                   float(P.single_body_length) - _scaled_allowance(P.single_body_length, P.basket_body_length_allowance))
    return float(P.basket_body_length)


def effective_basket_body_width():
    if P.derive_basket_from_single:
        if getattr(P, "basket_lower_body_fits_inside_single", True):
            # Parametric lower-body rule in Y.
            return max(float(P.basket_min_body_dimension),
                       single_inner_width() - 2.0 * basket_to_single_clearance_y())
        return max(float(P.basket_min_body_dimension),
                   float(P.single_body_width) - _scaled_allowance(P.single_body_width, P.basket_body_width_allowance))
    return float(P.basket_body_width)


def effective_basket_wall():
    return _small_dimension_wall(P.basket_wall, effective_basket_body_length(), effective_basket_body_width(), fraction=0.30)


def effective_basket_bottom():
    return min(float(P.basket_bottom), max(0.10, effective_basket_depth() - 0.50))


def effective_basket_lip_length():
    if P.derive_basket_from_single:
        return effective_basket_body_length() + 2.0 * P.basket_lip_overhang_x
    return P.basket_lip_length


def effective_basket_lip_width():
    if P.derive_basket_from_single:
        return effective_basket_body_width() + 2.0 * P.basket_lip_overhang_y
    return P.basket_lip_width


def effective_main_height():
    """Main holder height after optional auto-expansion for tall single inserts.

    The user-facing parameter P.main_height is treated as a minimum. When
    auto_expand_main_height_to_single is enabled, the generated main container is
    made tall enough that the single-container body can hang into the holder while
    still leaving the closed bottom intact.

    Important: once the single-container flange sits down inside a top recess,
    the body bottom moves down by main_single_container_recess_depth(). Therefore
    the required holder height must include that recess depth. Otherwise the
    single-container body can overlap the closed bottom.
    """
    h = float(P.main_height)
    if getattr(P, "auto_expand_main_height_to_single", True):
        needed = (
            float(P.single_depth)
            + main_single_container_recess_depth()
            + float(P.main_bottom_thickness)
            + max(0.0, float(P.z_clearance))
        )
        h = max(h, needed)
    return h


def main_insert_bottom_clearance():
    """Clearance between the inserted single-container bottom and the closed main bottom."""
    return main_insert_z() - float(P.main_bottom_thickness)


def effective_basket_depth():
    """Basket body depth.

    By default this keeps the earlier shallow-basket behaviour. If a user later
    sets basket_bottom larger than basket_depth, effective_basket_bottom() clamps
    the bottom thickness so FreeCAD does not receive a negative box height.
    """
    d = float(P.basket_depth)
    if getattr(P, "auto_expand_basket_depth_to_bottom", False):
        d = max(d, float(P.basket_bottom) + max(1.0, float(P.basket_min_open_depth)))
    return max(0.50, d)


def dish_window_length():
    return effective_basket_body_length() + 2.0 * P.fit_clearance_xy


def dish_window_width():
    return effective_basket_body_width() + 2.0 * P.fit_clearance_xy


def single_flange_length():
    return main_opening_length() + 2.0 * P.single_top_flange_overhang


def single_flange_width():
    return main_opening_width() + 2.0 * P.single_top_flange_overhang


def basket_total_height():
    return effective_basket_depth() + P.basket_lip_thickness


def grid_centres(pitch_x, pitch_y):
    """Return 2 x 2 centres: lower-left, lower-right, upper-left, upper-right."""
    return [
        (-pitch_x / 2.0, -pitch_y / 2.0),
        ( pitch_x / 2.0, -pitch_y / 2.0),
        (-pitch_x / 2.0,  pitch_y / 2.0),
        ( pitch_x / 2.0,  pitch_y / 2.0),
    ]


def opening_centres():
    return grid_centres(main_opening_length() + effective_opening_gap_x(),
                        main_opening_width() + effective_opening_gap_y())


def alignment_pin_position_mode():
    return str(getattr(P, "alignment_pin_position_mode", "strip_center")).strip().lower()


def alignment_pin_required_surround_radius():
    """Radial clearance needed around one alignment pin/bolt centre."""
    return alignment_fastener_outer_diameter() / 2.0 + max(0.0, float(P.alignment_pin_min_surround))


def alignment_pin_inset_from_outer_edge_x():
    return max(0.0, float(getattr(P, "alignment_pin_inset_from_outer_edge_x", 8.0)))


def alignment_pin_inset_from_outer_edge_y():
    return max(0.0, float(getattr(P, "alignment_pin_inset_from_outer_edge_y", 8.0)))


def alignment_pin_positions():
    """Internal pin/bolt positions inside the main footprint.

    Two positioning modes are supported:
      - strip_center: old behaviour, pins/bolts are centred in the available
        solid perimeter strip outside the 2 x 2 opening group.
      - inset_from_outer_edge: explicit user control. Increasing the inset moves
        the fastener farther from the outside wall and closer to the centre.
    """
    L = effective_main_outer_length()
    W = effective_main_outer_width()
    strip_x = (L - main_bay_length()) / 2.0
    strip_y = (W - main_bay_width()) / 2.0

    mode = alignment_pin_position_mode()
    if mode in {"inset", "inset_from_outer_edge", "edge_inset", "outer_inset"}:
        y_abs = W / 2.0 - alignment_pin_inset_from_outer_edge_y()
        positions = [(0.0, -y_abs), (0.0, y_abs)]
        if int(P.alignment_pin_count) >= 4:
            x_abs = L / 2.0 - alignment_pin_inset_from_outer_edge_x()
            positions.extend([(-x_abs, 0.0), (x_abs, 0.0)])
        return positions

    # Backward-compatible default: centre in the available perimeter strip.
    y_abs = main_bay_width() / 2.0 + strip_y / 2.0
    positions = [(0.0, -y_abs), (0.0, y_abs)]
    if int(P.alignment_pin_count) >= 4:
        x_abs = main_bay_length() / 2.0 + strip_x / 2.0
        positions.extend([(-x_abs, 0.0), (x_abs, 0.0)])
    return positions

def validate_parameters():
    if P.main_bottom_thickness <= 0:
        raise ValueError("main_bottom_thickness must be positive because the bottom must remain closed.")
    if P.main_bottom_thickness >= effective_main_height() - 2.0:
        raise ValueError("main_bottom_thickness is too large for main_height.")
    if main_insert_bottom_clearance() < -1e-6:
        needed = (
            float(P.single_depth)
            + main_single_container_recess_depth()
            + float(P.main_bottom_thickness)
            + max(0.0, float(P.z_clearance))
        )
        raise ValueError(
            "main_height is too short for the inserted single container and top recess. "
            f"Use main_height >= {needed:.2f} mm or set auto_expand_main_height_to_single=True."
        )
    if P.main_min_wall_thickness <= 0:
        raise ValueError("main_min_wall_thickness must be positive.")
    if main_side_wall_thickness() <= 0:
        raise ValueError("main_side_wall_thickness must be positive.")
    if 2.0 * main_side_wall_thickness() >= min(effective_main_outer_length(), effective_main_outer_width()):
        raise ValueError("main_side_wall_thickness is too large for the generated main-container footprint.")
    if modular_slots_enabled():
        needed_slot_backwall = float(P.modular_slot_depth) + float(P.modular_slot_min_back_wall)
        if main_side_wall_thickness() < needed_slot_backwall - 1e-6:
            raise ValueError(
                "main_side_wall_thickness is too small for the modular side slots; "
                f"use >= {needed_slot_backwall:.2f} mm or reduce modular_slot_depth/back-wall."
            )
    if float(getattr(P, "main_opening_side_margin_x", 0.0)) <= 0 or float(getattr(P, "main_opening_side_margin_y", 0.0)) <= 0:
        raise ValueError("main_opening_side_margin_x/y must be positive.")
    if single_container_recess_enabled():
        if main_single_container_recess_depth() <= 0:
            raise ValueError("main_single_container_recess_depth must be positive when the insert-seat recess is enabled.")
        max_recess_depth = min(
            effective_main_height() - P.main_bottom_thickness - 1.0,
            max(0.25, float(P.main_top_bridge_height) - 0.25),
        )
        if main_single_container_recess_depth() > max_recess_depth + 1e-6:
            raise ValueError(
                "main_single_container_recess_depth is too deep for the preserved top bridge/rib. "
                f"Use <= {max_recess_depth:.2f} mm, or increase main_top_bridge_height."
            )
        if main_single_container_recess_depth() > P.single_top_flange_thickness + 1e-6:
            App.Console.PrintWarning(
                "main_single_container_recess_depth is deeper than single_top_flange_thickness; "
                "the single-container flange top will sit below the main rim and the dish will rest on the main rim.\n"
            )
        # Ensure the four flange seats do not overlap each other or break through the outer edge.
        if effective_opening_gap_x() < 2.0 * main_single_container_recess_overhang_x() + 0.5:
            raise ValueError("opening_gap_x is too small for the single-container flange recesses.")
        if effective_opening_gap_y() < 2.0 * main_single_container_recess_overhang_y() + 0.5:
            raise ValueError("opening_gap_y is too small for the single-container flange recesses.")
    if main_bay_length() >= effective_main_outer_length():
        raise ValueError("Main opening group does not fit in X.")
    if main_bay_width() >= effective_main_outer_width():
        raise ValueError("Main opening group does not fit in Y.")
    if P.connect_main_wells_internally:
        if P.main_top_bridge_height <= 0:
            raise ValueError("main_top_bridge_height must be positive to preserve four separate top openings.")
        if P.main_bottom_thickness + P.main_top_bridge_height >= effective_main_height():
            raise ValueError("main_bottom_thickness + main_top_bridge_height must be less than main_height.")
    if P.single_body_length <= 0 or P.single_body_width <= 0:
        raise ValueError("single_body_length and single_body_width must be positive.")
    if effective_single_wall() <= 0:
        raise ValueError("Effective single-container wall thickness must be positive.")
    if P.single_depth <= effective_single_bottom() + 0.5:
        raise ValueError("Single-container depth must be larger than effective bottom thickness.")
    if P.dish_basket_lip_recess_depth >= P.dish_thickness:
        raise ValueError("Dish lip recess depth must be less than dish_thickness.")
    if getattr(P, "basket_lower_body_fits_inside_single", True):
        if getattr(P, "basket_clearance_follows_fit_clearance", True):
            if P.fit_clearance_xy < 0:
                raise ValueError("fit_clearance_xy must be non-negative when basket clearance follows it.")
        else:
            if P.basket_to_single_inner_clearance_x < 0 or P.basket_to_single_inner_clearance_y < 0:
                raise ValueError("basket_to_single_inner_clearance_x/y must be non-negative.")
        if P.basket_min_body_dimension <= 0:
            raise ValueError("basket_min_body_dimension must be positive.")
        if effective_basket_body_length() > single_inner_length() + 1e-6:
            raise ValueError("Basket lower body length is larger than the single-container internal length.")
        if effective_basket_body_width() > single_inner_width() + 1e-6:
            raise ValueError("Basket lower body width is larger than the single-container internal width.")
    if effective_basket_body_length() <= 0 or effective_basket_body_width() <= 0:
        raise ValueError("Effective basket footprint must be positive.")
    if effective_basket_wall() <= 0:
        raise ValueError("Effective basket wall thickness must be positive.")
    if effective_basket_depth() <= effective_basket_bottom() + 0.5:
        raise ValueError("Effective basket depth must be larger than effective basket bottom.")
    if effective_basket_lip_length() <= dish_window_length() or effective_basket_lip_width() <= dish_window_width():
        raise ValueError("Basket lip must be larger than the dish window so the dish can carry it.")
    if P.enable_alignment_pins:
        if alignment_fastener_outer_diameter() <= 0 or effective_alignment_fastener_height() <= 0:
            raise ValueError("Alignment pin/bolt diameter and height must be positive.")
        if alignment_bolt_and_nut_enabled():
            if alignment_bolt_core_diameter() > alignment_fastener_outer_diameter() + 1e-6:
                raise ValueError("alignment_bolt_core_diameter must be <= alignment_bolt_thread_outer_diameter.")
            if float(getattr(P, "alignment_bolt_thread_pitch", 0.0)) <= 0:
                raise ValueError("alignment_bolt_thread_pitch must be positive in bolt mode.")
            if float(getattr(P, "alignment_nut_across_flats", 0.0)) <= alignment_nut_bore_diameter() + 1.0:
                raise ValueError("alignment_nut_across_flats is too small for the nut bore.")
            if float(getattr(P, "alignment_nut_thickness", 0.0)) <= 0:
                raise ValueError("alignment_nut_thickness must be positive.")
        if P.alignment_pin_min_surround < 0.3:
            raise ValueError("alignment_pin_min_surround should leave printable material around the pin/bolt.")
        strip_y = (effective_main_outer_width() - main_bay_width()) / 2.0
        strip_x = (effective_main_outer_length() - main_bay_length()) / 2.0
        req_r = alignment_pin_required_surround_radius()
        if strip_y < 2.0 * req_r - 1e-6:
            raise ValueError("Y perimeter strip is too narrow for internal alignment pins/bolts.")
        if int(P.alignment_pin_count) >= 4 and strip_x < 2.0 * req_r - 1e-6:
            raise ValueError("X perimeter strip is too narrow for four internal alignment pins/bolts.")

        mode = alignment_pin_position_mode()
        if mode in {"inset", "inset_from_outer_edge", "edge_inset", "outer_inset"}:
            min_y = req_r
            max_y = strip_y - req_r
            if not (min_y - 1e-6 <= alignment_pin_inset_from_outer_edge_y() <= max_y + 1e-6):
                raise ValueError(
                    "alignment_pin_inset_from_outer_edge_y places the front/back bolts outside the safe solid strip. "
                    f"Use {min_y:.2f} to {max_y:.2f} mm, or increase main_opening_side_margin_y."
                )
            if int(P.alignment_pin_count) >= 4:
                min_x = req_r
                max_x = strip_x - req_r
                if not (min_x - 1e-6 <= alignment_pin_inset_from_outer_edge_x() <= max_x + 1e-6):
                    raise ValueError(
                        "alignment_pin_inset_from_outer_edge_x places the left/right bolts outside the safe solid strip. "
                        f"Use {min_x:.2f} to {max_x:.2f} mm, or increase main_opening_side_margin_x."
                    )
        elif mode not in {"strip_center", "center", "centre", "mid_strip"}:
            raise ValueError(
                "alignment_pin_position_mode must be 'strip_center' or 'inset_from_outer_edge'."
            )
    if modular_slots_enabled():
        if P.modular_slot_depth <= 0 or P.modular_slot_height <= 0:
            raise ValueError("modular_slot_depth and modular_slot_height must be positive.")
        if P.modular_slot_min_back_wall < 0.6:
            raise ValueError("modular_slot_min_back_wall should leave a printable sealed wall behind each slot.")
        if P.modular_key_clearance < 0:
            raise ValueError("modular_key_clearance must be non-negative.")
        if P.modular_module_gap < 0:
            raise ValueError("modular_module_gap must be non-negative.")
        zmin = P.modular_slot_z_center - P.modular_slot_height / 2.0
        zmax = P.modular_slot_z_center + P.modular_slot_height / 2.0
        if zmin <= P.main_bottom_thickness + 0.5:
            raise ValueError("Modular side slot is too low; keep it above the closed bottom.")
        if zmax >= effective_main_height() - 1.0:
            raise ValueError("Modular side slot is too high; keep it below the top rim/dish region.")
        strip_x = (effective_main_outer_length() - main_bay_length()) / 2.0
        strip_y = (effective_main_outer_width() - main_bay_width()) / 2.0
        sides = _normalise_modular_slot_sides()
        needed = P.modular_slot_depth + P.modular_slot_min_back_wall
        if ({"E", "W"} & sides) and strip_x < needed - 1e-6:
            raise ValueError("X perimeter strip is too narrow for E/W modular side slots.")
        if ({"N", "S"} & sides) and strip_y < needed - 1e-6:
            raise ValueError("Y perimeter strip is too narrow for N/S modular side slots.")
        if P.modular_slot_length_x <= 0 or P.modular_slot_length_y <= 0:
            raise ValueError("modular_slot_length_x/y must be positive.")
        if int(getattr(P, "modular_array_count_x", 1)) < 1 or int(getattr(P, "modular_array_count_y", 1)) < 1:
            raise ValueError("modular_array_count_x/y must be at least 1.")
    if modular_top_locks_enabled():
        if P.modular_lock_pin_diameter <= 0 or P.modular_lock_pin_depth <= 0:
            raise ValueError("modular_lock_pin_diameter/depth must be positive.")
        if P.modular_lock_pin_clearance < 0:
            raise ValueError("modular_lock_pin_clearance must be non-negative.")
        if P.modular_lock_pin_depth >= effective_main_height() - P.main_bottom_thickness - 1.0:
            raise ValueError("modular_lock_pin_depth is too deep for the main container height.")
        if P.modular_lock_pin_inset_from_outer_edge <= 0:
            raise ValueError("modular_lock_pin_inset_from_outer_edge must be positive.")
        if P.modular_lock_bridge_thickness <= 0 or P.modular_lock_bridge_width <= 0:
            raise ValueError("modular_lock_bridge_thickness/width must be positive.")
        if P.modular_lock_bridge_land_on_module <= 0:
            raise ValueError("modular_lock_bridge_land_on_module must be positive.")
        if P.modular_lock_bridge_pin_engagement <= 0:
            raise ValueError("modular_lock_bridge_pin_engagement must be positive.")
        if P.modular_lock_bridge_pin_engagement > P.modular_lock_pin_depth + 0.25:
            raise ValueError("Bridge pin engagement should not exceed blind socket depth.")
        sides = _normalise_modular_lock_sides()
        strip_x = (effective_main_outer_length() - main_bay_length()) / 2.0
        strip_y = (effective_main_outer_width() - main_bay_width()) / 2.0
        required = modular_lock_required_wall_strip()
        if ({"E", "W"} & sides) and strip_x < required - 1e-6:
            raise ValueError("X perimeter strip is too narrow for modular top-lock sockets.")
        if ({"N", "S"} & sides) and strip_y < required - 1e-6:
            raise ValueError("Y perimeter strip is too narrow for modular top-lock sockets.")
        if int(getattr(P, "modular_array_count_x", 1)) < 1 or int(getattr(P, "modular_array_count_y", 1)) < 1:
            raise ValueError("modular_array_count_x/y must be at least 1.")
    if physical_central_column_enabled():
        if P.central_column_diameter <= 0:
            raise ValueError("central_column_diameter must be positive.")
        if P.central_column_bore_diameter >= P.central_column_diameter - 1.0:
            raise ValueError("central_column_bore_diameter is too large; leave tube wall thickness.")
        if P.central_column_bore_bottom_z <= P.main_bottom_thickness:
            raise ValueError("central_column_bore_bottom_z must be above main_bottom_thickness so the bottom remains closed.")
        if P.central_column_bore_bottom_z >= effective_main_height() - 2.0:
            raise ValueError("central_column_bore_bottom_z is too high.")
        if P.central_column_port_diameter <= 0:
            raise ValueError("central_column_port_diameter must be positive.")
        if P.central_column_port_min_z <= P.central_column_bore_bottom_z:
            raise ValueError("central_column_port_min_z should be above the blind bore bottom.")
        if P.central_column_port_max_z >= effective_main_height() - 1.0:
            raise ValueError("central_column_port_max_z should remain below the top surface.")
        if P.central_column_port_min_z > P.central_column_port_max_z:
            raise ValueError("central_column_port_min_z must be <= central_column_port_max_z.")
        if int(P.central_column_port_levels) < 1:
            raise ValueError("central_column_port_levels must be at least 1.")


# -----------------------------------------------------------------------------
# Geometry helpers
# -----------------------------------------------------------------------------
def box_centered(length, width, height, zmin=0.0, x=0.0, y=0.0):
    return Part.makeBox(
        float(length), float(width), float(height),
        App.Vector(float(x - length / 2.0), float(y - width / 2.0), float(zmin))
    )


def cylinder_z(diameter, height, zmin=0.0, x=0.0, y=0.0):
    return Part.makeCylinder(
        float(diameter) / 2.0,
        float(height),
        App.Vector(float(x), float(y), float(zmin)),
        App.Vector(0, 0, 1),
    )


def cylinder_x(diameter, length, z=0.0, x=0.0, y=0.0):
    return Part.makeCylinder(
        float(diameter) / 2.0,
        float(length),
        App.Vector(float(x - length / 2.0), float(y), float(z)),
        App.Vector(1, 0, 0),
    )


def cylinder_y(diameter, length, z=0.0, x=0.0, y=0.0):
    return Part.makeCylinder(
        float(diameter) / 2.0,
        float(length),
        App.Vector(float(x), float(y - length / 2.0), float(z)),
        App.Vector(0, 1, 0),
    )


def modular_side_slot_cutters():
    """Blind rectangular side-slot cutters for the main holder.

    These are intentionally simple printable recesses. The connector key bridges
    two opposing recesses. Recess depth is limited by validation so the slots do
    not open into the liquid cavity.
    """
    if not modular_slots_enabled():
        return []
    L = effective_main_outer_length()
    W = effective_main_outer_width()
    sides = _normalise_modular_slot_sides()
    zmin = float(P.modular_slot_z_center) - float(P.modular_slot_height) / 2.0
    d = float(P.modular_slot_depth)
    eps = 0.08
    cutters = []

    # North/south faces: slot length is along X; recess cuts inward along Y.
    slot_len_x = min(float(P.modular_slot_length_x), max(1.0, L - 2.0 * P.main_min_wall_thickness))
    if "N" in sides:
        cutters.append(Part.makeBox(slot_len_x, d + eps, float(P.modular_slot_height),
                                    App.Vector(-slot_len_x / 2.0, W / 2.0 - d, zmin)))
    if "S" in sides:
        cutters.append(Part.makeBox(slot_len_x, d + eps, float(P.modular_slot_height),
                                    App.Vector(-slot_len_x / 2.0, -W / 2.0 - eps, zmin)))

    # East/west faces: slot length is along Y; recess cuts inward along X.
    slot_len_y = min(float(P.modular_slot_length_y), max(1.0, W - 2.0 * P.main_min_wall_thickness))
    if "E" in sides:
        cutters.append(Part.makeBox(d + eps, slot_len_y, float(P.modular_slot_height),
                                    App.Vector(L / 2.0 - d, -slot_len_y / 2.0, zmin)))
    if "W" in sides:
        cutters.append(Part.makeBox(d + eps, slot_len_y, float(P.modular_slot_height),
                                    App.Vector(-L / 2.0 - eps, -slot_len_y / 2.0, zmin)))
    return cutters


def modular_connector_key_shape(orientation="EW"):
    """Separate key that bridges two neighbouring module side slots.

    orientation="EW" connects west/east neighbours. orientation="NS" connects
    south/north neighbours. The key is one removable printed part, not fused to
    the main container.
    """
    orientation = str(orientation).strip().upper()
    clearance = max(0.0, float(P.modular_key_clearance))
    tongue_depth = max(0.2, float(P.modular_slot_depth) - clearance)
    gap = max(0.0, float(P.modular_module_gap))
    key_height = max(0.3, float(P.modular_slot_height) - 2.0 * clearance)
    zmin = float(P.modular_slot_z_center) - key_height / 2.0

    if orientation == "NS":
        key_x = max(0.5, float(P.modular_slot_length_x) - 2.0 * clearance)
        key_y = 2.0 * tongue_depth + gap
        return box_centered(key_x, key_y, key_height, zmin, 0.0, 0.0)

    key_x = 2.0 * tongue_depth + gap
    key_y = max(0.5, float(P.modular_slot_length_y) - 2.0 * clearance)
    return box_centered(key_x, key_y, key_height, zmin, 0.0, 0.0)


def _clamped_lock_pair_offsets(total_span):
    """Two pin offsets along a joint, centred and clamped to printable limits."""
    pin_d = float(P.modular_lock_pin_diameter) + float(P.modular_lock_pin_clearance)
    end_margin = max(float(P.modular_lock_pin_min_end_margin), pin_d)
    max_half = max(0.0, float(total_span) / 2.0 - end_margin)
    half = min(float(P.modular_lock_pin_pair_spacing) / 2.0, max_half)
    if half < pin_d * 0.65:
        return [0.0]
    return [-half, half]


def modular_lock_socket_positions_local():
    """Return blind top-socket centres for one main container, grouped by side.

    Sockets are placed in the solid outer perimeter strips, away from the removable
    single containers. E/W sockets use two Y offsets; N/S sockets use two X offsets.
    """
    if not modular_top_locks_enabled():
        return {}
    L = effective_main_outer_length()
    W = effective_main_outer_width()
    inset = float(P.modular_lock_pin_inset_from_outer_edge)
    sides = _normalise_modular_lock_sides()
    x_edge = max(-L / 2.0, L / 2.0 - inset)
    y_edge = max(-W / 2.0, W / 2.0 - inset)
    y_offsets = _clamped_lock_pair_offsets(W)
    x_offsets = _clamped_lock_pair_offsets(L)
    out = {}
    if "E" in sides:
        out["E"] = [(x_edge, y) for y in y_offsets]
    if "W" in sides:
        out["W"] = [(-x_edge, y) for y in y_offsets]
    if "N" in sides:
        out["N"] = [(x, y_edge) for x in x_offsets]
    if "S" in sides:
        out["S"] = [(x, -y_edge) for x in x_offsets]
    return out


def modular_lock_socket_cutters():
    """Blind vertical top-socket cutters for positive-lock bridge pins."""
    if not modular_top_locks_enabled():
        return []
    socket_d = float(P.modular_lock_pin_diameter) + float(P.modular_lock_pin_clearance)
    depth = float(P.modular_lock_pin_depth)
    top_z = effective_main_height()
    eps = 0.08
    cutters = []
    for centres in modular_lock_socket_positions_local().values():
        for x, y in centres:
            cutters.append(cylinder_z(socket_d, depth + eps, top_z - depth, x, y))
    return cutters


def modular_top_lock_bridge_shape(orientation="EW"):
    """Separate removable bridge with downward pins.

    EW bridges connect west/east neighbours; NS bridges connect south/north
    neighbours. The bridge plate sits above the main-container rim and its pins
    drop into blind sockets. This is a positive lock, unlike the older friction key.
    """
    orientation = str(orientation).strip().upper()
    gap = max(0.0, float(P.modular_module_gap))
    land = float(P.modular_lock_bridge_land_on_module)
    bridge_w = float(P.modular_lock_bridge_width)
    bridge_t = float(P.modular_lock_bridge_thickness)
    clearance = max(0.0, float(P.modular_lock_pin_clearance))
    pin_d = max(0.2, float(P.modular_lock_pin_diameter) - clearance)
    pin_len = max(0.5, min(float(P.modular_lock_bridge_pin_engagement),
                           float(P.modular_lock_pin_depth) - float(P.modular_lock_bridge_pin_tip_clearance)))
    z_plate = effective_main_height() + float(P.modular_lock_bridge_top_clearance)

    shapes = []
    if orientation == "NS":
        # Plate spans the Y gap and lands on both neighbouring modules.
        plate_len_y = gap + 2.0 * land
        plate = box_centered(bridge_w, plate_len_y, bridge_t, z_plate, 0.0, 0.0)
        shapes.append(plate)
        x_offsets = _clamped_lock_pair_offsets(effective_main_outer_length())
        y_pin = gap / 2.0 + float(P.modular_lock_pin_inset_from_outer_edge)
        for x in x_offsets:
            for y in (-y_pin, y_pin):
                shapes.append(cylinder_z(pin_d, pin_len, z_plate - pin_len, x, y))
        return fuse_many(shapes)

    # EW bridge: plate spans the X gap and lands on both neighbouring modules.
    plate_len_x = gap + 2.0 * land
    plate = box_centered(plate_len_x, bridge_w, bridge_t, z_plate, 0.0, 0.0)
    shapes.append(plate)
    y_offsets = _clamped_lock_pair_offsets(effective_main_outer_width())
    x_pin = gap / 2.0 + float(P.modular_lock_pin_inset_from_outer_edge)
    for x in (-x_pin, x_pin):
        for y in y_offsets:
            shapes.append(cylinder_z(pin_d, pin_len, z_plate - pin_len, x, y))
    return fuse_many(shapes)


def modular_central_cross_lock_shape():
    """Optional one-piece cross plate at the 2 x 2 centre.

    It uses the same four neighbouring socket groups around the central junction.
    It is useful for a 2 x 2 array that may be moved as one water-filled unit.
    """
    size = float(P.modular_cross_lock_plate_size)
    t = float(P.modular_cross_lock_plate_thickness)
    gap = max(0.0, float(P.modular_module_gap))
    clearance = max(0.0, float(P.modular_lock_pin_clearance))
    pin_d = max(0.2, float(P.modular_lock_pin_diameter) - clearance)
    pin_len = max(0.5, min(float(P.modular_lock_bridge_pin_engagement),
                           float(P.modular_lock_pin_depth) - float(P.modular_lock_bridge_pin_tip_clearance)))
    z_plate = effective_main_height() + float(P.modular_lock_bridge_top_clearance)
    shapes = [box_centered(size, size, t, z_plate, 0.0, 0.0)]
    # Four pins, one near each module corner around the central array joint.
    pin_offset = gap / 2.0 + float(P.modular_lock_pin_inset_from_outer_edge)
    for x in (-pin_offset, pin_offset):
        for y in (-pin_offset, pin_offset):
            shapes.append(cylinder_z(pin_d, pin_len, z_plate - pin_len, x, y))
    return fuse_many(shapes)


def modular_module_pitch_x():
    return effective_main_outer_length() + max(0.0, float(P.modular_module_gap))


def modular_module_pitch_y():
    return effective_main_outer_width() + max(0.0, float(P.modular_module_gap))


def modular_array_centres():
    nx = max(1, int(getattr(P, "modular_array_count_x", 1)))
    ny = max(1, int(getattr(P, "modular_array_count_y", 1)))
    px = modular_module_pitch_x()
    py = modular_module_pitch_y()
    x0 = -(nx - 1) * px / 2.0
    y0 = -(ny - 1) * py / 2.0
    out = []
    for j in range(ny):
        for i in range(nx):
            out.append((i + 1, j + 1, x0 + i * px, y0 + j * py))
    return out


def safe_remove_splitter(shape):
    try:
        return shape.removeSplitter()
    except Exception:
        return shape


def safe_fillet(shape, radius):
    if radius is None or radius <= 0:
        return shape
    try:
        return shape.makeFillet(float(radius), shape.Edges)
    except Exception:
        return shape


def cut_many(shape, cutters):
    out = shape
    for c in cutters:
        out = out.cut(c)
    return safe_remove_splitter(out)


def fuse_many(shapes):
    if not shapes:
        raise ValueError("No shapes to fuse.")
    out = shapes[0]
    for s in shapes[1:]:
        out = out.fuse(s)
    return safe_remove_splitter(out)


def add_feature(doc, name, shape, placement=None, color=None, transparency=None):
    obj = doc.addObject("Part::Feature", name)
    obj.Label = name
    obj.Shape = shape
    if placement is not None:
        obj.Placement = placement
    if Gui is not None and hasattr(obj, "ViewObject"):
        if color is not None:
            obj.ViewObject.ShapeColor = color
        if transparency is not None:
            obj.ViewObject.Transparency = transparency
    return obj


def clone_shape_feature(doc, name, source_shape, x=0.0, y=0.0, z=0.0, color=None, transparency=None):
    pl = App.Placement(App.Vector(x, y, z), App.Rotation())
    return add_feature(doc, name, source_shape, pl, color, transparency)


def dish_handle_style():
    return str(getattr(P, "dish_handle_style", "flat_tab")).strip().lower()


def dish_handle_shape(zmin, height):
    """Optional handle(s) for the dish only; the main box stays rectangular.

    Styles:
      - flat_tab: old horizontal solid tabs at the X ends of the dish.
      - vertical_hollow: upright U/loop handles at the X ends. The opening is
        hollow because the geometry is made from two side posts plus a top bridge,
        rather than a solid plate.
    """
    if not P.enable_dish_handle:
        return None

    style = dish_handle_style()
    if style in {"vertical", "vertical_hollow", "upright", "upright_hollow", "loop"}:
        L = effective_dish_outer_length()
        W = effective_dish_outer_width()
        span_y = min(float(P.dish_handle_width), max(1.0, W - 1.0))
        frame_wall = max(0.5, float(getattr(P, "dish_vertical_handle_wall", 3.0)))
        x_thick = max(0.5, float(getattr(P, "dish_vertical_handle_thickness_x", 4.0)))
        handle_h = max(frame_wall + 1.0, float(getattr(P, "dish_vertical_handle_height", 22.0)))
        inset = max(0.0, float(getattr(P, "dish_vertical_handle_inset_from_end", 1.0)))
        penetration = max(0.0, float(getattr(P, "dish_vertical_handle_base_penetration", 0.20)))

        # Keep the handle frame physically valid and ensure the central grip is open.
        post_w = min(frame_wall, span_y / 2.0 - 0.25)
        if post_w <= 0.2:
            raise ValueError("dish_handle_width is too small for the vertical hollow handle posts.")
        top_bar_h = min(frame_wall, handle_h - 0.5)

        z_post = float(P.dish_thickness) - penetration
        post_h = handle_h + penetration
        z_top_bar = float(P.dish_thickness) + handle_h - top_bar_h

        def one_vertical_handle(sign):
            x_center = sign * (L / 2.0 - inset - x_thick / 2.0)
            if abs(x_center) + x_thick / 2.0 > L / 2.0 + 1e-6:
                raise ValueError("Vertical dish handle is outside the dish footprint; increase dish_outer_length or reduce dish_vertical_handle_thickness_x/inset.")
            y_abs = span_y / 2.0 - post_w / 2.0
            shapes = [
                box_centered(x_thick, post_w, post_h, z_post, x_center, -y_abs),
                box_centered(x_thick, post_w, post_h, z_post, x_center,  y_abs),
                box_centered(x_thick, span_y, top_bar_h, z_top_bar, x_center, 0.0),
            ]
            return fuse_many(shapes)

        handles = [one_vertical_handle(1.0)]
        if P.dish_handle_both_ends:
            handles.append(one_vertical_handle(-1.0))
        return fuse_many(handles)

    if style not in {"flat", "flat_tab", "tab", "horizontal"}:
        raise ValueError("dish_handle_style must be 'flat_tab' or 'vertical_hollow'.")

    # Legacy flat horizontal tab handle.
    L = effective_dish_outer_length()
    handle_len = P.dish_handle_length + P.dish_handle_overlap
    x_abs = L / 2.0 + (P.dish_handle_length - P.dish_handle_overlap) / 2.0
    handles = [box_centered(handle_len, P.dish_handle_width, height, zmin, x_abs, 0.0)]
    if P.dish_handle_both_ends:
        handles.append(box_centered(handle_len, P.dish_handle_width, height, zmin, -x_abs, 0.0))
    return fuse_many(handles)

def central_port_z_positions():
    n = int(P.central_column_port_levels)
    if n <= 1:
        return [(P.central_column_port_min_z + P.central_column_port_max_z) / 2.0]
    step = (P.central_column_port_max_z - P.central_column_port_min_z) / float(n - 1)
    return [P.central_column_port_min_z + i * step for i in range(n)]


def central_column_internal_cutters():
    """Blind top bore plus radial ports. No cutter reaches the bottom face."""
    cutters = []
    if not physical_central_column_enabled():
        return cutters
    bore_height = effective_main_height() - P.central_column_bore_bottom_z + 2.0
    cutters.append(cylinder_z(P.central_column_bore_diameter,
                              bore_height,
                              P.central_column_bore_bottom_z,
                              0.0, 0.0))
    port_len = P.central_column_diameter + 2.0
    for z in central_port_z_positions():
        cutters.append(cylinder_x(P.central_column_port_diameter, port_len, z, 0.0, 0.0))
        cutters.append(cylinder_y(P.central_column_port_diameter, port_len, z, 0.0, 0.0))
    return cutters


def rectangle_union_area(rects):
    """Exact union area for axis-aligned rectangles. rect=(xmin,xmax,ymin,ymax)."""
    xs = sorted({r[0] for r in rects} | {r[1] for r in rects})
    if len(xs) < 2:
        return 0.0
    area = 0.0
    for x0, x1 in zip(xs[:-1], xs[1:]):
        if x1 <= x0:
            continue
        intervals = []
        xm = (x0 + x1) / 2.0
        for rx0, rx1, ry0, ry1 in rects:
            if rx0 <= xm <= rx1:
                intervals.append((ry0, ry1))
        if not intervals:
            continue
        intervals.sort()
        merged = []
        for y0, y1 in intervals:
            if not merged or y0 > merged[-1][1]:
                merged.append([y0, y1])
            else:
                merged[-1][1] = max(merged[-1][1], y1)
        y_total = sum(y1 - y0 for y0, y1 in merged)
        area += (x1 - x0) * y_total
    return area


def opening_rectangles():
    rects = []
    L = main_opening_length()
    W = main_opening_width()
    for x, y in opening_centres():
        rects.append((x - L / 2.0, x + L / 2.0, y - W / 2.0, y + W / 2.0))
    return rects


def main_lower_cross_section_area_mm2():
    # Lower chamber geometry is now governed by main_side_wall_thickness: the
    # outside dimensions remain fixed, and the internal liquid cavity is shaved
    # from the inside to leave that wall thickness. This keeps volume estimates
    # consistent with the generated lower cavity.
    area = main_lower_cavity_length() * main_lower_cavity_width()
    if physical_central_column_enabled():
        # Nominal displacement of the solid column within the connected lower area.
        area -= math.pi * (P.central_column_diameter / 2.0) ** 2
        # The blind bore is intentionally ignored for side calibration marks.
    return max(0.0, area)

def main_upper_cross_section_area_mm2():
    # Above the internal communication channel, only the four top opening columns are open.
    return 4.0 * main_opening_length() * main_opening_width()


def single_inner_cross_section_area_mm2():
    return max(0.0, (P.single_body_length - 2.0 * effective_single_wall()) *
                   (P.single_body_width - 2.0 * effective_single_wall()))


def single_container_capacity_ml():
    return single_inner_cross_section_area_mm2() * (P.single_depth - effective_single_bottom()) / 1000.0


def main_container_capacity_ml():
    lower_h = effective_main_height() - P.main_bottom_thickness - P.main_top_bridge_height
    upper_h = P.main_top_bridge_height
    return (main_lower_cross_section_area_mm2() * lower_h +
            main_upper_cross_section_area_mm2() * upper_h) / 1000.0


def single_level_z_for_volume_ml(ml):
    area = single_inner_cross_section_area_mm2()
    if area <= 0:
        return None
    h = float(ml) * 1000.0 / area
    if h <= 0 or h >= (P.single_depth - effective_single_bottom()):
        return None
    return effective_single_bottom() + h


def main_level_z_for_volume_ml(ml):
    lower_area = main_lower_cross_section_area_mm2()
    upper_area = main_upper_cross_section_area_mm2()
    if lower_area <= 0 or upper_area <= 0:
        return None
    lower_h = effective_main_height() - P.main_bottom_thickness - P.main_top_bridge_height
    v_mm3 = float(ml) * 1000.0
    v_lower = lower_area * lower_h
    if v_mm3 <= v_lower:
        h = v_mm3 / lower_area
    else:
        h = lower_h + (v_mm3 - v_lower) / upper_area
    if h <= 0 or h >= (effective_main_height() - P.main_bottom_thickness):
        return None
    return P.main_bottom_thickness + h


def single_volume_mark_max_z():
    """Highest allowed z for volume bars on the single-container side wall.

    The top exclusion zone is measured from the physical top of the insert, including
    its top flange. This keeps markings away from the upper ~20 mm while still
    allowing a 25 mL label on the default insert if it is below that exclusion zone.
    """
    physical_top = P.single_depth + P.single_top_flange_thickness
    return max(effective_single_bottom(), physical_top - max(0.0, P.volume_mark_top_exclusion_mm))


def main_volume_mark_max_z():
    """Highest allowed z for volume bars on the main-container side wall."""
    return max(P.main_bottom_thickness, effective_main_height() - max(0.0, P.volume_mark_top_exclusion_mm))


def volume_label_text(ml):
    return str(int(ml))


# Simple stroke text. This avoids dependency on a font file.
_DIGIT_SEGS = {
    "0": "ABCFED", "1": "BC", "2": "ABGED", "3": "ABGCD", "4": "FBGC",
    "5": "AFGCD", "6": "AFGECD", "7": "ABC", "8": "ABCDEFG", "9": "ABFGCD",
}

# Seven-segment-style approximations for uppercase letters. This keeps labels
# printable/exportable without relying on external font files. It is intentionally
# simple but supports changing part_label_prefix from A to any A-Z letter.
_LETTER_SEGS = {
    "A": "ABCEFG", "B": "CDEFG", "C": "ADEF", "D": "BCDEG", "E": "ADEFG",
    "F": "AEFG", "G": "ACDEF", "H": "BCEFG", "I": "BC", "J": "BCD",
    "K": "BEFG", "N": "CEG", "O": "ABCDEF", "P": "ABEFG", "Q": "ABCFG",
    "R": "EG", "S": "ACDFG", "T": "DEFG", "U": "BCDEF", "V": "CDE",
    "X": "BCEFG", "Y": "BCDFG", "Z": "ABDEG",
}


def stroke_rects_for_char(ch, scale, stroke):
    ch = ch.upper()
    W = 3.0 * scale
    H = 5.0 * scale
    s = stroke
    seg_rects = {
        "A": (0.15 * scale, W - 0.15 * scale, H - s, H),
        "G": (0.15 * scale, W - 0.15 * scale, H / 2.0 - s / 2.0, H / 2.0 + s / 2.0),
        "D": (0.15 * scale, W - 0.15 * scale, 0.0, s),
        "F": (0.0, s, H / 2.0, H),
        "B": (W - s, W, H / 2.0, H),
        "E": (0.0, s, 0.0, H / 2.0),
        "C": (W - s, W, 0.0, H / 2.0),
    }
    if ch in _DIGIT_SEGS:
        return [seg_rects[k] for k in _DIGIT_SEGS[ch]]
    if ch in _LETTER_SEGS:
        return [seg_rects[k] for k in _LETTER_SEGS[ch]]
    if ch == "M":
        # Blocky M: two verticals and two short upper diagonals approximated by vertical strokes.
        return [seg_rects["F"], seg_rects["E"], seg_rects["B"], seg_rects["C"],
                (W * 0.38 - s / 2.0, W * 0.38 + s / 2.0, H * 0.45, H),
                (W * 0.62 - s / 2.0, W * 0.62 + s / 2.0, H * 0.45, H)]
    if ch == "L":
        return [seg_rects["F"], seg_rects["E"], seg_rects["D"]]
    if ch == "W":
        return [seg_rects["F"], seg_rects["E"], seg_rects["B"], seg_rects["C"],
                (W * 0.38 - s / 2.0, W * 0.38 + s / 2.0, 0.0, H * 0.55),
                (W * 0.62 - s / 2.0, W * 0.62 + s / 2.0, 0.0, H * 0.55)]
    if ch == "-":
        return [seg_rects["G"]]
    return []


def stroke_text_width(label, scale):
    total = 0.0
    for ch in str(label):
        total += (2.0 if ch == " " else 4.0) * scale
    return max(0.0, total - scale)


def labels_are_engraved():
    return str(getattr(P, "label_style", "engraved")).strip().lower().startswith("engr")


def volume_marks_are_engraved():
    return str(getattr(P, "volume_mark_style", "engraved")).strip().lower().startswith("engr")


def top_text_shapes(label, center_x, center_y, zmin, scale, stroke, height):
    """Stroke text made of rectangular prisms on a horizontal surface."""
    shapes = []
    label = str(label)
    total_w = stroke_text_width(label, scale)
    char_h = 5.0 * scale
    x_cursor = center_x - total_w / 2.0
    y_base = center_y - char_h / 2.0
    for ch in label:
        if ch == " ":
            x_cursor += 2.0 * scale
            continue
        for x0, x1, y0, y1 in stroke_rects_for_char(ch, scale, stroke):
            shapes.append(box_centered(x1 - x0, y1 - y0, height,
                                       zmin,
                                       x_cursor + (x0 + x1) / 2.0,
                                       y_base + (y0 + y1) / 2.0))
        x_cursor += 4.0 * scale
    return shapes


def top_part_label_shapes(label, center_x, center_y, z_top, scale, stroke):
    """Return raised features or engraving cutters for a top-surface part label."""
    if labels_are_engraved():
        depth = max(0.05, float(P.label_depth))
        # Cutters cross the top surface slightly to make boolean cuts more reliable.
        return top_text_shapes(label, center_x, center_y, z_top - depth, scale, stroke, depth + 0.08)
    height = max(0.05, float(P.label_raised_height))
    return top_text_shapes(label, center_x, center_y, z_top, scale, stroke, height)


def side_y_text_shapes(label, y_face, x_center, z_center, protrude_negative_y, scale, stroke, projection):
    shapes = []
    label = str(label)
    total_w = stroke_text_width(label, scale)
    char_h = 5.0 * scale
    x_cursor = x_center - total_w / 2.0
    z_base = z_center - char_h / 2.0
    y0 = y_face - projection if protrude_negative_y else y_face
    for ch in label:
        if ch == " ":
            x_cursor += 2.0 * scale
            continue
        for x0, x1, yy0, yy1 in stroke_rects_for_char(ch, scale, stroke):
            shapes.append(Part.makeBox(x1 - x0, projection, yy1 - yy0,
                                       App.Vector(x_cursor + x0, y0, z_base + yy0)))
        x_cursor += 4.0 * scale
    return shapes


def side_y_text_cut_shapes(label, y_face, x_center, z_center, scale, stroke, depth):
    """Stroke text cutters for the negative-Y side face; cuts inward without protrusion."""
    shapes = []
    label = str(label)
    total_w = stroke_text_width(label, scale)
    char_h = 5.0 * scale
    x_cursor = x_center - total_w / 2.0
    z_base = z_center - char_h / 2.0
    outside_eps = 0.05
    y0 = y_face - outside_eps
    y_depth = max(0.05, float(depth)) + outside_eps
    for ch in label:
        if ch == " ":
            x_cursor += 2.0 * scale
            continue
        for x0, x1, yy0, yy1 in stroke_rects_for_char(ch, scale, stroke):
            shapes.append(Part.makeBox(x1 - x0, y_depth, yy1 - yy0,
                                       App.Vector(x_cursor + x0, y0, z_base + yy0)))
        x_cursor += 4.0 * scale
    return shapes


def side_y_bar_shape(x_center, y_face, z_center, length, thickness_z):
    """Volume tick mark as a raised feature or an engraved cutter on the negative-Y face."""
    if volume_marks_are_engraved():
        outside_eps = 0.05
        depth = max(0.05, float(P.volume_mark_depth)) + outside_eps
        return Part.makeBox(float(length), depth, float(thickness_z),
                            App.Vector(float(x_center - length / 2.0),
                                       float(y_face - outside_eps),
                                       float(z_center - thickness_z / 2.0)))
    return box_centered(length, P.volume_bar_projection, thickness_z,
                        z_center - thickness_z / 2.0,
                        x_center,
                        y_face - P.volume_bar_projection / 2.0)


def fuse_optional_features(base_shape, feature_shapes):
    feature_shapes = [s for s in feature_shapes if s is not None]
    if not feature_shapes:
        return base_shape
    return fuse_many([base_shape] + feature_shapes)


def apply_part_label_features(base_shape, label_shapes):
    label_shapes = [s for s in label_shapes if s is not None]
    if not label_shapes:
        return base_shape
    if labels_are_engraved():
        return cut_many(base_shape, label_shapes)
    return fuse_many([base_shape] + label_shapes)


def apply_volume_mark_features(base_shape, mark_shapes):
    mark_shapes = [s for s in mark_shapes if s is not None]
    if not mark_shapes:
        return base_shape
    if volume_marks_are_engraved():
        return cut_many(base_shape, mark_shapes)
    return fuse_many([base_shape] + mark_shapes)


def main_label_shapes():
    if not P.enable_part_labels:
        return []
    shapes = []
    wall_strip_y = (effective_main_outer_width() - main_bay_width()) / 2.0
    y_edge_offset = max(1.2, min(wall_strip_y * 0.55, 4.0))
    labels = [part_label(i) for i in range(1, 5)]
    for label, (x, y) in zip(labels, opening_centres()):
        # Put labels on the outer top wall adjacent to each opening, not floating over the openings.
        y_label = y - math.copysign(main_opening_width() / 2.0 + y_edge_offset, y)
        # For lower row y is negative, above expression moves label outward; for upper row outward too.
        if y < 0:
            y_label = y - main_opening_width() / 2.0 - y_edge_offset
        else:
            y_label = y + main_opening_width() / 2.0 + y_edge_offset
        shapes.extend(top_part_label_shapes(label, x, y_label, effective_main_height(), P.main_label_scale,
                                           P.label_stroke_width))
    return shapes


def single_label_shapes(label):
    if not P.enable_part_labels:
        return []
    # On the front flange, away from the open cup.
    y = -single_flange_width() / 2.0 + max(2.0, P.single_top_flange_overhang * 0.75)
    return top_part_label_shapes(label, 0.0, y, P.single_depth + P.single_top_flange_thickness,
                                 P.single_label_scale, P.label_stroke_width)


def basket_label_shapes(label):
    if not P.enable_part_labels:
        return []
    y = -effective_basket_lip_width() / 2.0 + max(1.6, P.basket_lip_overhang_y * 0.7)
    return top_part_label_shapes(label, 0.0, y, basket_total_height(),
                                 P.basket_label_scale, P.label_stroke_width)


def dish_label_shapes():
    if not P.enable_part_labels:
        return []
    shapes = []
    labels = [part_label(i) for i in range(1, 5)]
    # Use the solid front/back dish frame beside each basket window. This keeps the
    # labels on printable material and away from the basket openings.
    pitch_y = main_opening_width() + effective_opening_gap_y()
    dish_window_group_width = pitch_y + dish_window_width()
    side_strip_y = max(0.0, (effective_dish_outer_width() - dish_window_group_width) / 2.0)
    outward_offset = max(1.2, min(side_strip_y * 0.50, 4.0))
    for label, (x, y) in zip(labels, opening_centres()):
        if y < 0:
            y_label = y - dish_window_width() / 2.0 - outward_offset
        else:
            y_label = y + dish_window_width() / 2.0 + outward_offset
        shapes.extend(top_part_label_shapes(label, x, y_label, P.dish_thickness,
                                           P.dish_label_scale, P.label_stroke_width))
    return shapes


def single_volume_bar_shapes():
    if not P.enable_volume_bars:
        return []
    shapes = []
    y_face = -P.single_body_width / 2.0
    x0 = -P.single_body_length / 2.0 + 1.5
    interval = max(1, int(P.volume_bar_interval_ml))
    capacity = single_container_capacity_ml()
    ml = interval
    max_mark_z = single_volume_mark_max_z()
    while ml < capacity - 0.1:
        z = single_level_z_for_volume_ml(ml)
        if z is not None and z <= max_mark_z + 1e-6:
            major = P.volume_bar_major_every_ml > 0 and (ml % int(P.volume_bar_major_every_ml) == 0)
            bar_len = P.volume_bar_length_major if major else P.volume_bar_length_minor
            shapes.append(side_y_bar_shape(x0 + bar_len / 2.0, y_face, z,
                                           bar_len, P.volume_bar_thickness_z))
            if P.volume_label_every_ml and (ml % int(P.volume_label_every_ml) == 0):
                if volume_marks_are_engraved():
                    shapes.extend(side_y_text_cut_shapes(volume_label_text(ml), y_face,
                                                         x0 + bar_len + 4.0, z,
                                                         P.volume_label_scale,
                                                         P.volume_label_stroke_width,
                                                         P.volume_mark_depth))
                else:
                    shapes.extend(side_y_text_shapes(volume_label_text(ml), y_face,
                                                     x0 + bar_len + 4.0, z,
                                                     True, P.volume_label_scale,
                                                     P.volume_label_stroke_width,
                                                     P.volume_bar_projection))
        ml += interval
    return shapes


def main_volume_bar_shapes():
    if not P.enable_volume_bars:
        return []
    shapes = []
    y_face = -effective_main_outer_width() / 2.0
    x0 = -effective_main_outer_length() / 2.0 + 3.0
    interval = max(1, int(P.volume_bar_interval_ml))
    capacity = main_container_capacity_ml()
    ml = interval
    max_mark_z = main_volume_mark_max_z()
    while ml < capacity - 0.1:
        z = main_level_z_for_volume_ml(ml)
        if z is not None and z <= max_mark_z + 1e-6:
            major = P.volume_bar_major_every_ml > 0 and (ml % int(P.volume_bar_major_every_ml) == 0)
            bar_len = P.volume_bar_length_major if major else P.volume_bar_length_minor
            shapes.append(side_y_bar_shape(x0 + bar_len / 2.0, y_face, z,
                                           bar_len, P.volume_bar_thickness_z))
            if P.volume_label_every_ml and (ml % int(P.volume_label_every_ml) == 0):
                if volume_marks_are_engraved():
                    shapes.extend(side_y_text_cut_shapes(volume_label_text(ml), y_face,
                                                         x0 + bar_len + 4.0, z,
                                                         P.volume_label_scale,
                                                         P.volume_label_stroke_width,
                                                         P.volume_mark_depth))
                else:
                    shapes.extend(side_y_text_shapes(volume_label_text(ml), y_face,
                                                     x0 + bar_len + 4.0, z,
                                                     True, P.volume_label_scale,
                                                     P.volume_label_stroke_width,
                                                     P.volume_bar_projection))
        ml += interval
    return shapes



# -----------------------------------------------------------------------------
# V18/V19 parametric-box curved slot/tab modular connector overrides
# -----------------------------------------------------------------------------
def _v18_curve_width(t, face_value, deep_value):
    """Smoothly widen a slot/tab from its face throat to its deeper body."""
    t = max(0.0, min(1.0, float(t)))
    power = max(0.10, float(P.modular_curve_power))
    shaped = math.sin(0.5 * math.pi * t) ** power
    return float(face_value) + (float(deep_value) - float(face_value)) * shaped


def _v18_closed_wire(points):
    pts = list(points)
    if pts[0] != pts[-1]:
        pts.append(pts[0])
    return Part.makePolygon(pts)


def _v18_wire_y_plane_vertical(y, tangent_center, z0, z1, tangent_width):
    u0 = tangent_center - tangent_width / 2.0
    u1 = tangent_center + tangent_width / 2.0
    return _v18_closed_wire([
        App.Vector(u0, y, z0), App.Vector(u1, y, z0),
        App.Vector(u1, y, z1), App.Vector(u0, y, z1),
    ])


def _v18_wire_x_plane_vertical(x, tangent_center, z0, z1, tangent_width):
    u0 = tangent_center - tangent_width / 2.0
    u1 = tangent_center + tangent_width / 2.0
    return _v18_closed_wire([
        App.Vector(x, u0, z0), App.Vector(x, u1, z0),
        App.Vector(x, u1, z1), App.Vector(x, u0, z1),
    ])


def _v18_wire_y_plane_horizontal(y, tangent_center, tangent_length, z_center, vertical_height):
    u0 = tangent_center - tangent_length / 2.0
    u1 = tangent_center + tangent_length / 2.0
    z0 = z_center - vertical_height / 2.0
    z1 = z_center + vertical_height / 2.0
    return _v18_closed_wire([
        App.Vector(u0, y, z0), App.Vector(u1, y, z0),
        App.Vector(u1, y, z1), App.Vector(u0, y, z1),
    ])


def _v18_wire_x_plane_horizontal(x, tangent_center, tangent_length, z_center, vertical_height):
    u0 = tangent_center - tangent_length / 2.0
    u1 = tangent_center + tangent_length / 2.0
    z0 = z_center - vertical_height / 2.0
    z1 = z_center + vertical_height / 2.0
    return _v18_closed_wire([
        App.Vector(x, u0, z0), App.Vector(x, u1, z0),
        App.Vector(x, u1, z1), App.Vector(x, u0, z1),
    ])


def _v18_side_slot_z_center():
    low = P.main_bottom_thickness + P.modular_side_slot_deep_height / 2.0 + 2.0
    high = effective_main_height() - P.modular_side_slot_deep_height / 2.0 - 3.0
    requested = float(P.modular_side_slot_z_fraction) * effective_main_height()
    return max(low, min(high, requested))


def _v18_top_slot_offsets(side):
    count = max(1, int(P.modular_top_slots_per_side))
    span = effective_main_outer_length() if side in ("N", "S") else effective_main_outer_width()
    if count == 1:
        return [0.0]
    max_offset = max(0.0, span / 2.0 - P.modular_top_slot_deep_width - 2.0)
    base = min(max_offset, span * float(P.modular_top_slot_offset_fraction))
    if count == 2:
        return [-base, base]
    if count <= 1 or base <= 0:
        return [0.0]
    return [(-base + 2.0 * base * i / float(count - 1)) for i in range(count)]


def _v18_top_vertical_slot_cutter(side, tangent_offset):
    """Top-open curved dovetail slot descending vertically from a side-wall top edge."""
    L = effective_main_outer_length()
    W = effective_main_outer_width()
    H = effective_main_height()
    depth = float(P.modular_slot_depth)
    eps = float(P.modular_boolean_eps)
    n = max(3, int(P.modular_curve_steps))
    z0 = H - float(P.modular_top_slot_vertical_length)
    z1 = H + eps
    wires = []
    for i in range(n):
        t = i / float(n - 1)
        width = _v18_curve_width(t, P.modular_top_slot_face_width, P.modular_top_slot_deep_width)
        if side == "N":
            coord = W / 2.0 + eps - (depth + eps) * t
            wires.append(_v18_wire_y_plane_vertical(coord, tangent_offset, z0, z1, width))
        elif side == "S":
            coord = -W / 2.0 - eps + (depth + eps) * t
            wires.append(_v18_wire_y_plane_vertical(coord, tangent_offset, z0, z1, width))
        elif side == "E":
            coord = L / 2.0 + eps - (depth + eps) * t
            wires.append(_v18_wire_x_plane_vertical(coord, tangent_offset, z0, z1, width))
        elif side == "W":
            coord = -L / 2.0 - eps + (depth + eps) * t
            wires.append(_v18_wire_x_plane_vertical(coord, tangent_offset, z0, z1, width))
        else:
            raise ValueError(f"Unknown modular side: {side}")
    return Part.makeLoft(wires, True)


def _v18_side_horizontal_slot_cutter(side, tangent_offset=0.0):
    """Curved dovetail slot whose long axis is horizontal on the side face."""
    L = effective_main_outer_length()
    W = effective_main_outer_width()
    depth = float(P.modular_slot_depth)
    eps = float(P.modular_boolean_eps)
    n = max(3, int(P.modular_curve_steps))
    zc = _v18_side_slot_z_center()
    tangent_length = float(P.modular_side_slot_horizontal_length)
    wires = []
    for i in range(n):
        t = i / float(n - 1)
        vertical_height = _v18_curve_width(t, P.modular_side_slot_face_height, P.modular_side_slot_deep_height)
        if side == "N":
            coord = W / 2.0 + eps - (depth + eps) * t
            wires.append(_v18_wire_y_plane_horizontal(coord, tangent_offset, tangent_length, zc, vertical_height))
        elif side == "S":
            coord = -W / 2.0 - eps + (depth + eps) * t
            wires.append(_v18_wire_y_plane_horizontal(coord, tangent_offset, tangent_length, zc, vertical_height))
        elif side == "E":
            coord = L / 2.0 + eps - (depth + eps) * t
            wires.append(_v18_wire_x_plane_horizontal(coord, tangent_offset, tangent_length, zc, vertical_height))
        elif side == "W":
            coord = -L / 2.0 - eps + (depth + eps) * t
            wires.append(_v18_wire_x_plane_horizontal(coord, tangent_offset, tangent_length, zc, vertical_height))
        else:
            raise ValueError(f"Unknown modular side: {side}")
    return Part.makeLoft(wires, True)


def modular_side_slot_cutters():
    """V18 connector slots: top-vertical plus side-horizontal; never bottom slots."""
    if not modular_slots_enabled():
        return []
    cutters = []
    for side in sorted(_normalise_modular_slot_sides()):
        if getattr(P, "enable_modular_top_vertical_slots", True):
            for offset in _v18_top_slot_offsets(side):
                cutters.append(_v18_top_vertical_slot_cutter(side, offset))
        if getattr(P, "enable_modular_side_horizontal_slots", True):
            cutters.append(_v18_side_horizontal_slot_cutter(side, 0.0))
    return cutters


def _v18_double_top_tab(orientation="NS", tangent_offset=0.0):
    """One recessed top-inserted double-sided curved tab with a smaller plier head."""
    orientation = str(orientation).upper()
    clear = max(0.0, float(P.modular_key_clearance))
    face_w = max(0.5, float(P.modular_top_slot_face_width) - clear)
    deep_w = max(face_w + 0.1, float(P.modular_top_slot_deep_width) - clear)
    half_depth = max(0.3, float(P.modular_slot_depth) - float(P.modular_fit_clearance_depth_per_side))
    total_depth = 2.0 * half_depth + max(0.0, float(P.modular_module_gap))
    head_h = max(0.4, float(P.modular_tab_head_height))
    body_len = max(1.0, float(P.modular_top_slot_vertical_length) - float(P.modular_top_tab_length_clearance) - head_h)
    n = max(3, int(P.modular_curve_steps))
    wires = []
    for i in range(2 * n - 1):
        s = i / float(2 * n - 2)
        normal = -total_depth / 2.0 + total_depth * s
        width = _v18_curve_width(abs(s - 0.5) * 2.0, face_w, deep_w)
        if orientation == "NS":
            wires.append(_v18_wire_y_plane_vertical(normal, tangent_offset, 0.0, body_len, width))
        else:
            wires.append(_v18_wire_x_plane_vertical(normal, tangent_offset, 0.0, body_len, width))
    body = Part.makeLoft(wires, True)

    # A narrow recessed head is smaller than the body and remains below the top surface.
    head_w = max(0.6, face_w * float(P.modular_tab_head_width_fraction))
    head_normal = max(0.4, float(P.modular_module_gap) + float(P.modular_tab_head_gap_depth))
    if orientation == "NS":
        head = box_centered(head_w, head_normal, head_h, body_len, tangent_offset, 0.0)
    else:
        head = box_centered(head_normal, head_w, head_h, body_len, 0.0, tangent_offset)
    shape = fuse_many([body, head])
    shape = safe_fillet(shape, float(P.modular_tab_edge_fillet))
    z_place = effective_main_height() - float(P.modular_top_tab_surface_recess) - (body_len + head_h)
    moved = shape.copy()
    moved.translate(App.Vector(0.0, 0.0, z_place))
    return moved


def _v18_double_side_tab(orientation="NS"):
    """One horizontal double-sided curved tab with a small recessed plier grip."""
    orientation = str(orientation).upper()
    clear = max(0.0, float(P.modular_key_clearance))
    face_h = max(0.5, float(P.modular_side_slot_face_height) - clear)
    deep_h = max(face_h + 0.1, float(P.modular_side_slot_deep_height) - clear)
    half_depth = max(0.3, float(P.modular_slot_depth) - float(P.modular_fit_clearance_depth_per_side))
    total_depth = 2.0 * half_depth + max(0.0, float(P.modular_module_gap))
    body_len = max(1.0, float(P.modular_side_slot_horizontal_length) - float(P.modular_side_tab_length_clearance))
    n = max(3, int(P.modular_curve_steps))
    wires = []
    for i in range(2 * n - 1):
        s = i / float(2 * n - 2)
        normal = -total_depth / 2.0 + total_depth * s
        height = _v18_curve_width(abs(s - 0.5) * 2.0, face_h, deep_h)
        if orientation == "NS":
            wires.append(_v18_wire_y_plane_horizontal(normal, 0.0, body_len, 0.0, height))
        else:
            wires.append(_v18_wire_x_plane_horizontal(normal, 0.0, body_len, 0.0, height))
    body = Part.makeLoft(wires, True)

    # Smaller plier heads extend into the intentionally unused slot length at
    # both ends. They remain inside the slot envelope, so they create no bump,
    # but an accessible end can be grasped with needle-nose pliers.
    spare_each_end = max(0.4, float(P.modular_side_tab_length_clearance) / 2.0)
    grip_tangent = max(0.5, min(float(P.modular_tab_head_length), spare_each_end * 0.85))
    grip_normal = max(0.4, float(P.modular_module_gap) + float(P.modular_tab_head_gap_depth))
    grip_height = max(0.5, face_h * float(P.modular_tab_head_width_fraction))
    grip_offset = body_len / 2.0 + grip_tangent / 2.0
    if orientation == "NS":
        grip_a = box_centered(grip_tangent, grip_normal, grip_height, -grip_height / 2.0, -grip_offset, 0.0)
        grip_b = box_centered(grip_tangent, grip_normal, grip_height, -grip_height / 2.0,  grip_offset, 0.0)
    else:
        grip_a = box_centered(grip_normal, grip_tangent, grip_height, -grip_height / 2.0, 0.0, -grip_offset)
        grip_b = box_centered(grip_normal, grip_tangent, grip_height, -grip_height / 2.0, 0.0,  grip_offset)
    shape = fuse_many([body, grip_a, grip_b])
    shape = safe_fillet(shape, float(P.modular_tab_edge_fillet))
    moved = shape.copy()
    moved.translate(App.Vector(0.0, 0.0, _v18_side_slot_z_center()))
    return moved


def modular_connector_key_shape(orientation="EW"):
    """Return the complete recessed connector set for one neighbouring-module joint.

    The compound contains two vertical top tabs plus one horizontal side tab.
    It has no blind top bridge and no protruding external handle.
    """
    orientation = str(orientation).strip().upper()
    tangent_side = "N" if orientation == "NS" else "E"
    shapes = []
    if getattr(P, "enable_modular_top_vertical_slots", True):
        for offset in _v18_top_slot_offsets(tangent_side):
            shapes.append(_v18_double_top_tab(orientation, offset))
    if getattr(P, "enable_modular_side_horizontal_slots", True):
        shapes.append(_v18_double_side_tab(orientation))
    return Part.makeCompound(shapes)


# Add v18-specific checks while preserving all earlier validation.
_validate_parameters_v17 = validate_parameters

def validate_parameters():
    _validate_parameters_v17()
    if not modular_slots_enabled():
        return
    if P.modular_top_slot_deep_width <= P.modular_top_slot_face_width:
        raise ValueError("modular_top_slot_deep_width must exceed modular_top_slot_face_width for dovetail locking.")
    if P.modular_side_slot_deep_height <= P.modular_side_slot_face_height:
        raise ValueError("modular_side_slot_deep_height must exceed modular_side_slot_face_height for dovetail locking.")
    if P.modular_top_slot_vertical_length <= P.modular_top_tab_length_clearance + P.modular_tab_head_height + 1.0:
        raise ValueError("Top slot must be longer than the recessed top tab plus its plier head.")
    if P.modular_side_slot_horizontal_length <= P.modular_side_tab_length_clearance + 1.0:
        raise ValueError("Horizontal side slot must be longer than its recessed tab.")
    if P.modular_slot_depth + P.modular_slot_min_back_wall > min(required_main_wall_strip_x(), required_main_wall_strip_y()) + 1e-6:
        raise ValueError("Modular slot depth/back-wall requirement exceeds the generated perimeter wall strip.")
    if P.modular_curve_steps < 3:
        raise ValueError("modular_curve_steps must be at least 3.")


# -----------------------------------------------------------------------------
# V19 edge-open modular connector overrides
# -----------------------------------------------------------------------------
def _v19_edge_slot_z_centres(side):
    """Return staggered side-edge slot heights for one side orientation."""
    side = str(side).upper()
    if side in ("N", "S"):
        fractions = tuple(getattr(P, "modular_edge_slot_z_fractions_ns", (0.30, 0.62)))
    else:
        fractions = tuple(getattr(P, "modular_edge_slot_z_fractions_ew", (0.44, 0.76)))
    requested_count = max(1, int(getattr(P, "modular_edge_slots_per_vertical_edge", 2)))
    if len(fractions) < requested_count:
        # Parametric fallback: evenly distribute requested levels while avoiding
        # the closed bottom and top rim.
        fractions = tuple((i + 1.0) / (requested_count + 1.0) for i in range(requested_count))
    H = effective_main_height()
    half_h = float(P.modular_edge_slot_deep_height) / 2.0
    z_min = float(P.main_bottom_thickness) + half_h + 2.0
    z_max = H - half_h - max(4.0, float(P.main_top_bridge_height))
    return [max(z_min, min(z_max, float(fractions[i]) * H)) for i in range(requested_count)]


def _v19_edge_tangent_center(side, edge_sign):
    """Centre an edge-open slot so one end reaches the selected vertical corner."""
    side = str(side).upper()
    edge_sign = 1.0 if float(edge_sign) >= 0 else -1.0
    span = effective_main_outer_length() if side in ("N", "S") else effective_main_outer_width()
    length = float(P.modular_edge_slot_insertion_length)
    eps = float(P.modular_boolean_eps)
    return edge_sign * (span / 2.0 - length / 2.0 + eps / 2.0)


def _v19_edge_vertical_slot_cutter(side, edge_sign, z_center):
    """Curved dovetail slot on a side face, open to a vertical corner edge.

    Its visible footprint is tall and narrow, matching the user's blue-marked
    edge position. The slot reaches the corner edge so the connector tab slides
    in horizontally from that edge rather than projecting from the flat wall.
    """
    L = effective_main_outer_length()
    W = effective_main_outer_width()
    depth = float(P.modular_slot_depth)
    eps = float(P.modular_boolean_eps)
    n = max(3, int(P.modular_curve_steps))
    tangent_center = _v19_edge_tangent_center(side, edge_sign)
    tangent_length = float(P.modular_edge_slot_insertion_length) + eps
    wires = []
    for i in range(n):
        t = i / float(n - 1)
        vertical_height = _v18_curve_width(
            t,
            P.modular_edge_slot_face_height,
            P.modular_edge_slot_deep_height,
        )
        if side == "N":
            coord = W / 2.0 + eps - (depth + eps) * t
            wires.append(_v18_wire_y_plane_horizontal(coord, tangent_center, tangent_length,
                                                       z_center, vertical_height))
        elif side == "S":
            coord = -W / 2.0 - eps + (depth + eps) * t
            wires.append(_v18_wire_y_plane_horizontal(coord, tangent_center, tangent_length,
                                                       z_center, vertical_height))
        elif side == "E":
            coord = L / 2.0 + eps - (depth + eps) * t
            wires.append(_v18_wire_x_plane_horizontal(coord, tangent_center, tangent_length,
                                                       z_center, vertical_height))
        elif side == "W":
            coord = -L / 2.0 - eps + (depth + eps) * t
            wires.append(_v18_wire_x_plane_horizontal(coord, tangent_center, tangent_length,
                                                       z_center, vertical_height))
        else:
            raise ValueError(f"Unknown modular side: {side}")
    return Part.makeLoft(wires, True)


def modular_side_slot_cutters():
    """V19 slots: retain top slots, remove flat-wall slots, add edge-open slots.

    No connector feature is added to the bottom. Every side has four edge slots:
    two vertical edges multiplied by two staggered height levels.
    """
    if not modular_slots_enabled():
        return []
    cutters = []
    for side in sorted(_normalise_modular_slot_sides()):
        if getattr(P, "enable_modular_top_vertical_slots", True):
            for offset in _v18_top_slot_offsets(side):
                cutters.append(_v18_top_vertical_slot_cutter(side, offset))
        if getattr(P, "enable_modular_edge_slots", True):
            for edge_sign in (-1.0, 1.0):
                for zc in _v19_edge_slot_z_centres(side):
                    cutters.append(_v19_edge_vertical_slot_cutter(side, edge_sign, zc))
    return cutters


def _v19_double_edge_tab(orientation="EW", edge_sign=1.0, z_center=0.0):
    """Double-sided connector tab for one pair of opposing edge-open slots.

    The main body is shorter than the slot. A smaller head occupies only part of
    the unused length near the edge, leaving a recess where needle-nose pliers can
    grip it for disassembly. Nothing projects beyond the module side envelope.
    """
    orientation = str(orientation).upper()
    edge_sign = 1.0 if float(edge_sign) >= 0 else -1.0
    clear = max(0.0, float(P.modular_key_clearance))
    face_h = max(0.5, float(P.modular_edge_slot_face_height) - clear)
    deep_h = max(face_h + 0.1, float(P.modular_edge_slot_deep_height) - clear)
    half_depth = max(0.3, float(P.modular_slot_depth) - float(P.modular_fit_clearance_depth_per_side))
    total_depth = 2.0 * half_depth + max(0.0, float(P.modular_module_gap))
    slot_len = float(P.modular_edge_slot_insertion_length)
    spare = max(0.8, float(P.modular_edge_tab_length_clearance))
    body_len = max(1.0, slot_len - spare)
    span = effective_main_outer_width() if orientation == "EW" else effective_main_outer_length()

    # Put the body against the inward end of the edge-open slot, leaving all
    # removable/grip clearance at the outside corner edge.
    tangent_center = edge_sign * (span / 2.0 - spare - body_len / 2.0)
    n = max(3, int(P.modular_curve_steps))
    wires = []
    for i in range(2 * n - 1):
        s = i / float(2 * n - 2)
        normal = -total_depth / 2.0 + total_depth * s
        height = _v18_curve_width(abs(s - 0.5) * 2.0, face_h, deep_h)
        if orientation == "EW":
            # Across an E/W joint: normal X, tangent Y.
            wires.append(_v18_wire_x_plane_horizontal(normal, tangent_center, body_len,
                                                       z_center, height))
        else:
            # Across an N/S joint: normal Y, tangent X.
            wires.append(_v18_wire_y_plane_horizontal(normal, tangent_center, body_len,
                                                       z_center, height))
    body = Part.makeLoft(wires, True)

    head_len = max(0.5, min(float(P.modular_edge_tab_head_length), spare * 0.70))
    head_height = max(0.5, face_h * float(P.modular_edge_tab_head_height_fraction))
    head_normal = max(0.4, float(P.modular_module_gap) + float(P.modular_tab_head_gap_depth))
    # Head starts where the body ends and points toward the accessible edge.
    head_tangent_center = edge_sign * (span / 2.0 - spare + head_len / 2.0)
    if orientation == "EW":
        head = box_centered(head_normal, head_len, head_height,
                            z_center - head_height / 2.0, 0.0, head_tangent_center)
    else:
        head = box_centered(head_len, head_normal, head_height,
                            z_center - head_height / 2.0, head_tangent_center, 0.0)
    return safe_fillet(fuse_many([body, head]), float(P.modular_tab_edge_fillet))


def modular_connector_key_shape(orientation="EW"):
    """Complete v19 connector set for one neighbouring-module joint.

    It contains the retained top-inserted tabs plus four edge tabs: two endpoint
    edges x two staggered height levels. The removed flat-wall horizontal tab is
    not generated.
    """
    orientation = str(orientation).strip().upper()
    shapes = []
    tangent_side = "E" if orientation == "EW" else "N"
    if getattr(P, "enable_modular_top_vertical_slots", True):
        for offset in _v18_top_slot_offsets(tangent_side):
            shapes.append(_v18_double_top_tab(orientation, offset))
    if getattr(P, "enable_modular_edge_slots", True):
        for edge_sign in (-1.0, 1.0):
            for zc in _v19_edge_slot_z_centres(tangent_side):
                shapes.append(_v19_double_edge_tab(orientation, edge_sign, zc))
    return Part.makeCompound(shapes)


_validate_parameters_v19_base = validate_parameters

def validate_parameters():
    _validate_parameters_v19_base()
    if not modular_slots_enabled() or not getattr(P, "enable_modular_edge_slots", True):
        return
    if int(P.modular_edge_slots_per_vertical_edge) < 1:
        raise ValueError("modular_edge_slots_per_vertical_edge must be at least 1.")
    if P.modular_edge_slot_insertion_length <= P.modular_edge_tab_length_clearance + 1.0:
        raise ValueError("Edge slot insertion length must exceed tab clearance plus 1 mm.")
    if P.modular_edge_slot_deep_height <= P.modular_edge_slot_face_height:
        raise ValueError("modular_edge_slot_deep_height must exceed face height for dovetail locking.")
    if P.modular_edge_tab_head_length >= P.modular_edge_tab_length_clearance:
        raise ValueError("Edge-tab head must be shorter than the unused slot length for plier access.")
    if P.modular_edge_slot_insertion_length >= min(effective_main_outer_length(), effective_main_outer_width()) / 2.0:
        raise ValueError("Edge slot insertion length is too large for the main-container footprint.")


def regular_prism_z(radius, sides, height, zmin=0.0, x=0.0, y=0.0, rotation_deg=30.0):
    """Regular polygon prism extruded in Z, used for printable hex nuts."""
    sides = max(3, int(sides))
    r = float(radius)
    pts = []
    rot = math.radians(float(rotation_deg))
    for i in range(sides):
        a = rot + 2.0 * math.pi * i / sides
        pts.append(App.Vector(float(x + r * math.cos(a)), float(y + r * math.sin(a)), float(zmin)))
    pts.append(pts[0])
    wire = Part.makePolygon(pts)
    face = Part.Face(wire)
    return face.extrude(App.Vector(0, 0, float(height)))


def make_alignment_fastener_shape(zmin, x=0.0, y=0.0):
    """Vertical alignment post or bolt-like post fused to the main container."""
    if not alignment_bolt_and_nut_enabled():
        return cylinder_z(P.alignment_pin_diameter, effective_alignment_fastener_height(), zmin, x, y)

    height = effective_alignment_fastener_height()
    core_d = alignment_bolt_core_diameter()
    outer_d = alignment_fastener_outer_diameter()
    shapes = [cylinder_z(core_d, height, zmin, x, y)]

    pitch = max(0.2, float(getattr(P, "alignment_bolt_thread_pitch", 1.0)))
    ridge_h = max(0.05, min(float(getattr(P, "alignment_bolt_thread_ridge_height", 0.25)), pitch * 0.75))
    base_h = max(0.0, float(getattr(P, "alignment_bolt_unthreaded_base_height", 0.0)))
    tip_clear = max(0.0, float(getattr(P, "alignment_bolt_tip_clearance", 0.0)))

    # Printable thread approximation: stacked raised rings. This avoids fragile
    # tiny helical threads while still giving the nut a mechanical/friction grip.
    z = float(zmin) + base_h + pitch * 0.5
    zmax = float(zmin) + height - tip_clear
    while z + ridge_h / 2.0 <= zmax:
        shapes.append(cylinder_z(outer_d, ridge_h, z - ridge_h / 2.0, x, y))
        z += pitch

    return fuse_many(shapes)


def make_alignment_nut_shape():
    """Separate printable hex nut for the alignment bolts."""
    across_flats = max(0.5, float(getattr(P, "alignment_nut_across_flats", 7.0)))
    radius = across_flats / math.sqrt(3.0)  # circumradius for requested across-flats size
    thickness = max(0.2, float(getattr(P, "alignment_nut_thickness", 3.0)))
    nut = regular_prism_z(radius, 6, thickness, 0.0, 0.0, 0.0, rotation_deg=30.0)

    bore = cylinder_z(alignment_nut_bore_diameter(), thickness + 2.0, -1.0, 0.0, 0.0)
    nut = nut.cut(bore)

    # Add shallow top/bottom relief holes to make the nut easier to start on the
    # printed bolt and reduce elephant-foot sensitivity.
    relief_d = alignment_nut_bore_diameter() + 0.35
    relief_h = min(0.45, thickness / 4.0)
    if relief_h > 0.05:
        nut = nut.cut(cylinder_z(relief_d, relief_h + 0.05, -0.02, 0.0, 0.0))
        nut = nut.cut(cylinder_z(relief_d, relief_h + 0.05, thickness - relief_h, 0.0, 0.0))

    nut = safe_remove_splitter(nut)
    nut = safe_fillet(nut, getattr(P, "alignment_nut_corner_fillet", 0.0))
    return nut

# -----------------------------------------------------------------------------
# Part builders
# -----------------------------------------------------------------------------
def make_main_container():
    """Main holder with one perimeter wall, closed bottom, connected lower wells.

    The only top openings are the four rectangular insert openings. Below the top
    bridge/rib, the four wells are connected through lower side channels. The
    bottom remains closed because all pocket/channel cuts start at or above
    main_bottom_thickness.
    """
    base = box_centered(effective_main_outer_length(), effective_main_outer_width(), effective_main_height(), 0.0)

    cutters = []

    # Four top pockets. They stop at the bottom-thickness plane.
    pocket_cut_height = effective_main_height() - P.main_bottom_thickness + 2.0
    for x, y in opening_centres():
        cutters.append(box_centered(main_opening_length(), main_opening_width(),
                                    pocket_cut_height,
                                    P.main_bottom_thickness,
                                    x, y))

    # Lower internal liquid-volume cavity. This shaves the side walls from the
    # inside only, so the outside dimensions remain unchanged while the lower
    # content volume expands to leave P.main_side_wall_thickness. The top
    # bridge/rib region is preserved so the four top openings and flange recesses
    # remain unchanged.
    lower_cavity_h = main_lower_cavity_height()
    if lower_cavity_h > 0:
        cutters.append(box_centered(main_lower_cavity_length(),
                                    main_lower_cavity_width(),
                                    lower_cavity_h,
                                    P.main_bottom_thickness,
                                    0.0, 0.0))

    # Shallow top seat/counterbore for the removable single-container flange.
    # This larger recess does not go through the part; the smaller through-opening
    # below remains the ledge that stops the insert from falling into the holder.
    if single_container_recess_enabled() and main_single_container_recess_depth() > 0:
        recess_depth = main_single_container_recess_depth()
        recess_zmin = effective_main_height() - recess_depth
        for x, y in opening_centres():
            cutters.append(box_centered(main_single_container_recess_length(),
                                        main_single_container_recess_width(),
                                        recess_depth + 0.08,
                                        recess_zmin,
                                        x, y))

    # Lower communication channels through internal divider walls only.
    if P.connect_main_wells_internally:
        channel_zmin = P.main_bottom_thickness
        channel_height = effective_main_height() - P.main_bottom_thickness - P.main_top_bridge_height
        channel_x = effective_opening_gap_x() + 2.0 * P.main_connection_overlap
        channel_y = effective_opening_gap_y() + 2.0 * P.main_connection_overlap
        cutters.append(box_centered(channel_x, main_bay_width(), channel_height, channel_zmin, 0.0, 0.0))
        cutters.append(box_centered(main_bay_length(), channel_y, channel_height, channel_zmin, 0.0, 0.0))

    # Remove bulky square junction material above the closed bottom, then add back
    # a cylindrical column. This keeps the bottom sealed while avoiding a double-wall look.
    if physical_central_column_enabled():
        cutout = P.central_column_diameter + 2.0 * P.central_column_cutout_clearance
        cutters.append(box_centered(cutout, cutout,
                                    effective_main_height() - P.main_bottom_thickness + 2.0,
                                    P.main_bottom_thickness,
                                    0.0, 0.0))

    # Blind modular side slots are outside-wall recesses only; validation ensures
    # a sealed back wall remains before the liquid cavity. They are alignment aids only.
    cutters.extend(modular_side_slot_cutters())

    # V17 bridge sockets are disabled in v18; no blind top-lock bridge is used.
    cutters.extend(modular_lock_socket_cutters())

    shape = cut_many(base, cutters)

    if physical_central_column_enabled():
        column = cylinder_z(P.central_column_diameter, effective_main_height(), 0.0, 0.0, 0.0)
        shape = fuse_many([shape, column])
        shape = cut_many(shape, central_column_internal_cutters())

    if P.enable_alignment_pins:
        fasteners = [make_alignment_fastener_shape(effective_main_height(), x, y)
                     for x, y in alignment_pin_positions()]
        shape = fuse_many([shape] + fasteners)

    shape = apply_part_label_features(shape, main_label_shapes())
    shape = apply_volume_mark_features(shape, main_volume_bar_shapes())

    shape = safe_fillet(shape, P.fillet_radius)
    return shape


def make_single_container(label=None):
    """One removable open-top insert container with a top lip/flange."""
    if label is None:
        label = part_label(1)
    sw = effective_single_wall()
    sb = effective_single_bottom()
    outer = box_centered(P.single_body_length, P.single_body_width, P.single_depth, 0.0)
    inner = box_centered(P.single_body_length - 2.0 * sw,
                         P.single_body_width - 2.0 * sw,
                         P.single_depth - sb + 1.0,
                         sb,
                         0.0, 0.0)
    cup = outer.cut(inner)

    flange = box_centered(single_flange_length(), single_flange_width(),
                          P.single_top_flange_thickness, P.single_depth)
    flange_hole = box_centered(P.single_body_length - 2.0 * sw,
                               P.single_body_width - 2.0 * sw,
                               P.single_top_flange_thickness + 2.0,
                               P.single_depth - 1.0)
    flange = flange.cut(flange_hole)

    shape = fuse_many([cup, flange])
    shape = apply_part_label_features(shape, single_label_shapes(label))
    shape = apply_volume_mark_features(shape, single_volume_bar_shapes())
    shape = safe_fillet(shape, P.single_corner_fillet)
    return shape


def make_dish():
    """Top dish/carrier plate with basket windows and matching alignment-pin holes."""
    plate = box_centered(effective_dish_outer_length(), effective_dish_outer_width(), P.dish_thickness, 0.0)

    if P.enable_dish_handle:
        handle = dish_handle_shape(0.0, P.dish_thickness)
        if handle is not None:
            plate = fuse_many([plate, handle])

    cutters = []
    for x, y in opening_centres():
        cutters.append(box_centered(dish_window_length(), dish_window_width(),
                                    P.dish_thickness + 2.0, -1.0, x, y))
        cutters.append(box_centered(effective_basket_lip_length() + P.dish_basket_lip_recess_clearance,
                                    effective_basket_lip_width() + P.dish_basket_lip_recess_clearance,
                                    P.dish_basket_lip_recess_depth + 0.05,
                                    P.dish_thickness - P.dish_basket_lip_recess_depth,
                                    x, y))

    # Central fill/access hole. This can remain present even when the physical
    # middle column is disabled in the main container.
    if dish_central_fill_hole_enabled() and P.dish_central_fill_hole_diameter > 0:
        cutters.append(cylinder_z(P.dish_central_fill_hole_diameter,
                                  P.dish_thickness + 2.0,
                                  -1.0, 0.0, 0.0))

    if P.enable_alignment_pins:
        pin_hole_d = alignment_fastener_hole_diameter()
        for x, y in alignment_pin_positions():
            cutters.append(cylinder_z(pin_hole_d, P.dish_thickness + 2.0, -1.0, x, y))

    shape = cut_many(plate, cutters)
    shape = apply_part_label_features(shape, dish_label_shapes())
    shape = safe_fillet(shape, P.fillet_radius)
    return shape


def make_basket(label=None):
    """One open-top plant basket with top lip and perforations."""
    if label is None:
        label = part_label(1)
    bw = effective_basket_wall()
    bb = effective_basket_bottom()
    bd = effective_basket_depth()
    body_outer = box_centered(effective_basket_body_length(), effective_basket_body_width(), bd, 0.0)
    body_inner = box_centered(effective_basket_body_length() - 2.0 * bw,
                              effective_basket_body_width() - 2.0 * bw,
                              bd - bb + 1.0,
                              bb)
    basket = body_outer.cut(body_inner)

    lip = box_centered(effective_basket_lip_length(), effective_basket_lip_width(),
                       P.basket_lip_thickness, bd)
    lip_hole = box_centered(effective_basket_body_length() - 2.0 * bw,
                            effective_basket_body_width() - 2.0 * bw,
                            P.basket_lip_thickness + 2.0,
                            bd - 1.0)
    lip = lip.cut(lip_hole)
    basket = basket.fuse(lip)

    cutters = []

    # Bottom drainage/root slots.
    usable_x = effective_basket_body_length() - 2.0 * bw - P.basket_bottom_slot_length
    usable_y = effective_basket_body_width() - 2.0 * bw - P.basket_bottom_slot_width
    nx = max(1, int(math.floor(usable_x / P.basket_bottom_slot_pitch_x)) + 1)
    ny = max(1, int(math.floor(usable_y / P.basket_bottom_slot_pitch_y)) + 1)
    for ix in range(nx):
        x = (ix - (nx - 1) / 2.0) * P.basket_bottom_slot_pitch_x
        for iy in range(ny):
            y = (iy - (ny - 1) / 2.0) * P.basket_bottom_slot_pitch_y
            cutters.append(box_centered(P.basket_bottom_slot_length,
                                        P.basket_bottom_slot_width,
                                        bb + 2.0,
                                        -1.0, x, y))

    # Long-wall side slots.
    slot_count_x = max(1, int((effective_basket_body_length() - 2.0 * bw) / P.basket_side_slot_pitch))
    for ix in range(slot_count_x):
        x = (ix - (slot_count_x - 1) / 2.0) * P.basket_side_slot_pitch
        for y in (-effective_basket_body_width() / 2.0, effective_basket_body_width() / 2.0):
            cutters.append(box_centered(P.basket_side_slot_length,
                                        bw * 3.0,
                                        P.basket_side_slot_height,
                                        P.basket_side_slot_z,
                                        x, y))

    # Short-wall side slots.
    slot_count_y = max(1, int((effective_basket_body_width() - 2.0 * bw) / P.basket_side_slot_pitch))
    for iy in range(slot_count_y):
        y = (iy - (slot_count_y - 1) / 2.0) * P.basket_side_slot_pitch
        for x in (-effective_basket_body_length() / 2.0, effective_basket_body_length() / 2.0):
            cutters.append(box_centered(bw * 3.0,
                                        P.basket_side_slot_length,
                                        P.basket_side_slot_height,
                                        P.basket_side_slot_z,
                                        x, y))

    basket = cut_many(basket, cutters)
    basket = apply_part_label_features(basket, basket_label_shapes(label))
    basket = safe_fillet(basket, P.basket_corner_fillet)
    return basket


# -----------------------------------------------------------------------------
# Assembly and export
# -----------------------------------------------------------------------------
def create_document():
    validate_parameters()

    doc = App.newDocument("PET_Plant_Container_V33")

    main_shape = make_main_container()
    dish_shape = make_dish()

    # Stack positions. The insert body extends down into the main opening; the flange
    # top is above the main holder. Dish sits above the insert flange.
    insert_z = main_insert_z()
    dish_z = main_dish_support_z() + P.z_clearance
    basket_z = dish_z + P.dish_thickness - effective_basket_depth()

    show_array = bool(getattr(P, "show_modular_array_preview", False))

    if show_array:
        # Modular preview: show an array of identical main containers. Each module
        # contains four openings, so a 2 x 2 preview represents 16 plant positions.
        for i, j, x, y in modular_array_centres():
            clone_shape_feature(doc, f"Main_Container_M{i}_{j}", main_shape, x, y, 0.0,
                                color=(0.78, 0.78, 0.78), transparency=35)

            if getattr(P, "modular_preview_show_dishes", False):
                clone_shape_feature(doc, f"Dish_M{i}_{j}", dish_shape, x, y, dish_z,
                                    color=(0.35, 0.55, 0.95), transparency=30)

            if getattr(P, "modular_preview_show_inserts", False):
                for k, (ox, oy) in enumerate(opening_centres(), start=1):
                    clone_shape_feature(doc, f"Single_Container_M{i}_{j}_{part_label_name(k)}",
                                        make_single_container(part_label(k)),
                                        x + ox, y + oy, insert_z,
                                        color=(0.40, 0.85, 0.55), transparency=45)

            if getattr(P, "modular_preview_show_baskets", False):
                for k, (ox, oy) in enumerate(opening_centres(), start=1):
                    clone_shape_feature(doc, f"Basket_M{i}_{j}_{part_label_name(k)}",
                                        make_basket(part_label(k)),
                                        x + ox, y + oy, basket_z,
                                        color=(0.95, 0.75, 0.35), transparency=15)

        nx = max(1, int(getattr(P, "modular_array_count_x", 1)))
        ny = max(1, int(getattr(P, "modular_array_count_y", 1)))
        px = modular_module_pitch_x()
        py = modular_module_pitch_y()
        x0 = -(nx - 1) * px / 2.0
        y0 = -(ny - 1) * py / 2.0

        if modular_slots_enabled() and getattr(P, "modular_preview_show_connector_keys", False):
            # V19 recessed curved-dovetail connector sets: retained top tabs
            # plus four edge-open tabs per neighbouring-module joint.
            ew_key = modular_connector_key_shape("EW")
            ns_key = modular_connector_key_shape("NS")
            for j in range(ny):
                y = y0 + j * py
                for i in range(nx - 1):
                    x = x0 + (i + 0.5) * px
                    clone_shape_feature(doc, f"Modular_Connector_Set_EW_{i+1}_{j+1}", ew_key, x, y, 0.0,
                                        color=(0.20, 0.20, 0.20), transparency=0)
            for j in range(ny - 1):
                y = y0 + (j + 0.5) * py
                for i in range(nx):
                    x = x0 + i * px
                    clone_shape_feature(doc, f"Modular_Connector_Set_NS_{i+1}_{j+1}", ns_key, x, y, 0.0,
                                        color=(0.20, 0.20, 0.20), transparency=0)

        if modular_top_locks_enabled() and getattr(P, "modular_preview_show_top_lock_bridges", True):
            ew_bridge = modular_top_lock_bridge_shape("EW")
            ns_bridge = modular_top_lock_bridge_shape("NS")
            # East-west top locks: one bridge between horizontal neighbours in each row.
            for j in range(ny):
                y = y0 + j * py
                for i in range(nx - 1):
                    x = x0 + (i + 0.5) * px
                    clone_shape_feature(doc, f"Top_Lock_Bridge_EW_{i+1}_{j+1}", ew_bridge, x, y, 0.0,
                                        color=(0.05, 0.05, 0.05), transparency=0)
            # North-south top locks: one bridge between vertical neighbours in each column.
            for j in range(ny - 1):
                y = y0 + (j + 0.5) * py
                for i in range(nx):
                    x = x0 + i * px
                    clone_shape_feature(doc, f"Top_Lock_Bridge_NS_{i+1}_{j+1}", ns_bridge, x, y, 0.0,
                                        color=(0.05, 0.05, 0.05), transparency=0)

            if (getattr(P, "enable_modular_central_cross_lock", False) and
                    getattr(P, "modular_preview_show_central_cross_lock", True) and nx == 2 and ny == 2):
                clone_shape_feature(doc, "Top_Central_Cross_Lock", modular_central_cross_lock_shape(),
                                    0.0, 0.0, 0.0, color=(0.02, 0.02, 0.02), transparency=0)

        if getattr(P, "modular_preview_show_reference_parts", True):
            # Place one representative dish/single/basket beside the array so their
            # unchanged mating dimensions remain visible without filling every module.
            nx = max(1, int(getattr(P, "modular_array_count_x", 1)))
            array_half_x = (nx - 1) * modular_module_pitch_x() / 2.0 + effective_main_outer_length() / 2.0
            x_ref = array_half_x + max(35.0, effective_dish_outer_length() / 2.0 + 20.0)
            clone_shape_feature(doc, "Reference_Dish", dish_shape, x_ref, 0.0, dish_z,
                                color=(0.35, 0.55, 0.95), transparency=30)
            clone_shape_feature(doc, f"Reference_Single_Container_{part_label_name(1)}", make_single_container(part_label(1)),
                                x_ref, -effective_dish_outer_width() / 2.0 - 20.0, 0.0,
                                color=(0.40, 0.85, 0.55), transparency=25)
            clone_shape_feature(doc, f"Reference_Basket_{part_label_name(1)}", make_basket(part_label(1)),
                                x_ref, effective_dish_outer_width() / 2.0 + 20.0, 0.0,
                                color=(0.95, 0.75, 0.35), transparency=5)
            if modular_slots_enabled() and getattr(P, "modular_preview_show_connector_keys", False):
                clone_shape_feature(doc, "Reference_Modular_Connector_Set_EW", modular_connector_key_shape("EW"),
                                    x_ref, effective_dish_outer_width() / 2.0 + 45.0, 0.0,
                                    color=(0.20, 0.20, 0.20), transparency=0)
                clone_shape_feature(doc, "Reference_Modular_Connector_Set_NS", modular_connector_key_shape("NS"),
                                    x_ref, effective_dish_outer_width() / 2.0 + 60.0, 0.0,
                                    color=(0.20, 0.20, 0.20), transparency=0)
            if modular_top_locks_enabled():
                clone_shape_feature(doc, "Reference_Top_Lock_Bridge_EW", modular_top_lock_bridge_shape("EW"),
                                    x_ref, effective_dish_outer_width() / 2.0 + 45.0, 0.0,
                                    color=(0.05, 0.05, 0.05), transparency=0)
                clone_shape_feature(doc, "Reference_Top_Lock_Bridge_NS", modular_top_lock_bridge_shape("NS"),
                                    x_ref, effective_dish_outer_width() / 2.0 + 65.0, 0.0,
                                    color=(0.05, 0.05, 0.05), transparency=0)
                if getattr(P, "enable_modular_central_cross_lock", False):
                    clone_shape_feature(doc, "Reference_Top_Central_Cross_Lock", modular_central_cross_lock_shape(),
                                        x_ref, effective_dish_outer_width() / 2.0 + 90.0, 0.0,
                                        color=(0.02, 0.02, 0.02), transparency=0)

    else:
        add_feature(doc, "Main_Container", main_shape, color=(0.78, 0.78, 0.78), transparency=35)
        add_feature(doc, "Dish", dish_shape,
                    App.Placement(App.Vector(0, 0, dish_z), App.Rotation()),
                    color=(0.35, 0.55, 0.95), transparency=30)

        if (P.enable_alignment_pins and alignment_bolt_and_nut_enabled() and
                bool(getattr(P, "show_alignment_nuts_in_assembly", True))):
            nut_shape = make_alignment_nut_shape()
            nut_z = alignment_nut_assembly_z(dish_z)
            for i, (nx_pos, ny_pos) in enumerate(alignment_pin_positions(), start=1):
                clone_shape_feature(doc, f"Alignment_Nut_{i}", nut_shape, nx_pos, ny_pos, nut_z,
                                    color=(0.08, 0.08, 0.08), transparency=0)

        centres = opening_centres()
        if P.add_four_insert_copies:
            for i, (x, y) in enumerate(centres, start=1):
                single_shape_i = make_single_container(part_label(i))
                clone_shape_feature(doc, f"Single_Container_{part_label_name(i)}", single_shape_i, x, y, insert_z,
                                    color=(0.40, 0.85, 0.55), transparency=45)
        else:
            x, y = centres[0]
            single_shape = make_single_container(part_label(1))
            clone_shape_feature(doc, f"Single_Container_{part_label_name(1)}", single_shape, x, y, insert_z,
                                color=(0.40, 0.85, 0.55), transparency=45)

        if P.add_four_basket_copies:
            for i, (x, y) in enumerate(centres, start=1):
                basket_shape_i = make_basket(part_label(i))
                clone_shape_feature(doc, f"Basket_{part_label_name(i)}", basket_shape_i, x, y, basket_z,
                                    color=(0.95, 0.75, 0.35), transparency=15)
        else:
            x, y = centres[0]
            basket_shape = make_basket(part_label(1))
            clone_shape_feature(doc, f"Basket_{part_label_name(1)}", basket_shape, x, y, basket_z,
                                color=(0.95, 0.75, 0.35), transparency=15)

        if P.add_reference_parts_to_side:
            x_ref = effective_main_outer_length() / 2.0 + 50.0
            clone_shape_feature(doc, f"Reference_Single_Container_{part_label_name(1)}", make_single_container(part_label(1)), x_ref, -20.0, 0.0,
                                color=(0.40, 0.85, 0.55), transparency=25)
            clone_shape_feature(doc, f"Reference_Basket_{part_label_name(1)}", make_basket(part_label(1)), x_ref, 25.0, 0.0,
                                color=(0.95, 0.75, 0.35), transparency=5)
            if modular_slots_enabled():
                clone_shape_feature(doc, "Reference_Modular_Key_EW", modular_connector_key_shape("EW"), x_ref, 50.0, 0.0,
                                    color=(0.15, 0.15, 0.15), transparency=0)
                clone_shape_feature(doc, "Reference_Modular_Key_NS", modular_connector_key_shape("NS"), x_ref, 65.0, 0.0,
                                    color=(0.15, 0.15, 0.15), transparency=0)
            if P.enable_alignment_pins and alignment_bolt_and_nut_enabled():
                clone_shape_feature(doc, "Reference_Alignment_Nut", make_alignment_nut_shape(), x_ref, 82.0, 0.0,
                                    color=(0.08, 0.08, 0.08), transparency=0)

    # Optional hidden annotation with critical mating/capacity dimensions. Disabled
    # by default because the user asked for Mating_Dimensions_Note not to be shown.
    if P.create_mating_dimensions_note:
        note = doc.addObject("App::Annotation", "Mating_Dimensions_Note")
        note.LabelText = [
            "Critical mating dimensions:",
            f"Main opening = {main_opening_length():.2f} x {main_opening_width():.2f} mm",
            f"Clear margin outside recess = {effective_clear_margin_outside_recess_x():.2f} mm X, {effective_clear_margin_outside_recess_y():.2f} mm Y",
            f"Through-opening edge-to-wall distance = {effective_main_opening_side_margin_x():.2f} mm X, {effective_main_opening_side_margin_y():.2f} mm Y",
            f"Single-container flange recess = {main_single_container_recess_length():.2f} x {main_single_container_recess_width():.2f} x {main_single_container_recess_depth():.2f} mm",
            f"Physical central column enabled = {physical_central_column_enabled()}",
            f"Single body = {P.single_body_length:.2f} x {P.single_body_width:.2f} mm",
            f"Dish window = {dish_window_length():.2f} x {dish_window_width():.2f} mm",
            f"Basket body = {effective_basket_body_length():.2f} x {effective_basket_body_width():.2f} mm",
            f"Single-container nominal capacity = {single_container_capacity_ml():.1f} mL",
            f"Main-container nominal capacity = {main_container_capacity_ml():.1f} mL",
            f"Nominal one-side XY clearance = {P.fit_clearance_xy:.2f} mm",
            f"Volume marks omitted above top {P.volume_mark_top_exclusion_mm:.1f} mm zone",
            f"Effective main outer = {effective_main_outer_length():.2f} x {effective_main_outer_width():.2f} x {effective_main_height():.2f} mm",
            f"Modular preview = {getattr(P, 'modular_array_count_x', 1)} x {getattr(P, 'modular_array_count_y', 1)} modules",
            f"Main bottom closed = YES; bottom thickness = {P.main_bottom_thickness:.2f} mm",
        ]
        note.Position = App.Vector(-effective_main_outer_length() / 2.0,
                                   -effective_main_outer_width() / 2.0 - 18.0,
                                   0.0)
        if Gui is not None and hasattr(note, "ViewObject"):
            note.ViewObject.Visibility = False

    App.Console.PrintMessage(f"Single-container nominal capacity: {single_container_capacity_ml():.1f} mL\n")
    App.Console.PrintMessage(f"Main-container nominal capacity: {main_container_capacity_ml():.1f} mL\n")
    App.Console.PrintMessage(f"Opening side margins: X={effective_main_opening_side_margin_x():.1f} mm, Y={effective_main_opening_side_margin_y():.1f} mm\n")
    App.Console.PrintMessage(f"Single-container seat recess depth: {main_single_container_recess_depth():.1f} mm\n")
    App.Console.PrintMessage(f"Dish handle style: {dish_handle_style()}\n")
    App.Console.PrintMessage(f"Physical central column enabled: {physical_central_column_enabled()}\n")
    App.Console.PrintMessage(f"Part label prefix: {part_label_prefix()} -> {part_label(1)}-{part_label(4)}\n")
    if show_array:
        total_modules = max(1, int(P.modular_array_count_x)) * max(1, int(P.modular_array_count_y))
        App.Console.PrintMessage(f"Modular preview: {P.modular_array_count_x} x {P.modular_array_count_y} modules = {total_modules * 4} plant openings\n")
        if modular_slots_enabled():
            App.Console.PrintMessage("Modular connector tabs are separate removable parts; flat-wall slots are removed and edge slots are blind recesses.\n")
    App.Console.PrintMessage(f"Volume bars/labels omitted above top {P.volume_mark_top_exclusion_mm:.1f} mm zone.\n")
    App.Console.PrintMessage(f"Main single-container recess depth: {main_single_container_recess_depth():.2f} mm\n")
    App.Console.PrintMessage(f"Effective main height: {effective_main_height():.2f} mm\n")
    App.Console.PrintMessage(f"Main lower side-wall thickness: {main_side_wall_thickness():.2f} mm\n")
    if P.enable_alignment_pins:
        App.Console.PrintMessage(f"Alignment fastener style: {getattr(P, 'alignment_fastener_style', 'pin')}\n")
        App.Console.PrintMessage(f"Alignment position mode: {alignment_pin_position_mode()}\n")
        if alignment_pin_position_mode() in {"inset", "inset_from_outer_edge", "edge_inset", "outer_inset"}:
            App.Console.PrintMessage(
                f"Alignment inset from outer edge: X={alignment_pin_inset_from_outer_edge_x():.2f} mm, "
                f"Y={alignment_pin_inset_from_outer_edge_y():.2f} mm\n"
            )
        App.Console.PrintMessage(f"Alignment fastener outer diameter: {alignment_fastener_outer_diameter():.2f} mm\n")
        App.Console.PrintMessage(f"Alignment fastener height: {effective_alignment_fastener_height():.2f} mm\n")
        if alignment_bolt_and_nut_enabled():
            App.Console.PrintMessage(f"Alignment nut bore: {alignment_nut_bore_diameter():.2f} mm; thickness: {P.alignment_nut_thickness:.2f} mm\n")

    App.Console.PrintMessage(f"Single-container bottom clearance above closed main bottom: {main_insert_bottom_clearance():.2f} mm\n")
    App.Console.PrintMessage(f"Main clear margin outside recess: X={effective_clear_margin_outside_recess_x():.2f} mm, Y={effective_clear_margin_outside_recess_y():.2f} mm\n")
    App.Console.PrintMessage(f"Main through-opening edge-to-wall distance: X={effective_main_opening_side_margin_x():.2f} mm, Y={effective_main_opening_side_margin_y():.2f} mm\n")

    doc.recompute()

    if Gui is not None:
        Gui.ActiveDocument.ActiveView.viewAxonometric()
        Gui.SendMsgToActiveView("ViewFit")

    maybe_export(doc)
    return doc

def maybe_export(doc):
    # Use getattr() so older/custom P blocks that omit export_* settings do not
    # crash at the end of document creation. Missing settings default to no export.
    export_step = bool(getattr(P, "export_step", False))
    export_stl = bool(getattr(P, "export_stl", False))
    if not (export_step or export_stl):
        return

    export_dir = getattr(
        P,
        "export_dir",
        os.path.join(os.path.expanduser("~"), "PET_plant_container_exports"),
    )
    os.makedirs(export_dir, exist_ok=True)

    export_visible_only = bool(getattr(P, "export_visible_only", False))
    export_objects = []
    for obj in doc.Objects:
        if obj.TypeId != "Part::Feature":
            continue
        if export_visible_only and hasattr(obj, "ViewObject") and not obj.ViewObject.Visibility:
            continue
        export_objects.append(obj)

    if export_step:
        import Import
        step_path = os.path.join(export_dir, "PET_plant_container_assembly.step")
        Import.export(export_objects, step_path)
        App.Console.PrintMessage(f"Exported STEP: {step_path}\n")

    if export_stl:
        import Mesh
        for obj in export_objects:
            stl_path = os.path.join(export_dir, f"{obj.Name}.stl")
            Mesh.export([obj], stl_path)
            App.Console.PrintMessage(f"Exported STL: {stl_path}\n")




# -----------------------------------------------------------------------------
# Revision v30 overrides — single large dish opening and threaded corner guides
# -----------------------------------------------------------------------------
# These overrides intentionally leave the main container, single container,
# basket, modular slots, labels, and volume-mark logic unchanged. Only the dish
# plate/opening behaviour and the new main-container corner guides are added.

# Default new parameters. They are assigned with hasattr() so any values you add
# manually inside class P above will not be overwritten.
if not hasattr(P, "use_single_large_dish_opening"):
    P.use_single_large_dish_opening = True

# Dish outer footprint: smaller than the main-container footprint by this gap on
# each side. Default 3 mm means dish L/W = main L/W - 6 mm.
if not hasattr(P, "dish_gap_from_main_x_edge"):
    P.dish_gap_from_main_x_edge = 3.0
if not hasattr(P, "dish_gap_from_main_y_edge"):
    P.dish_gap_from_main_y_edge = 3.0

# One large central dish opening. These gaps are measured from the outside edges
# of the MAIN container, not from the smaller dish edge.
if not hasattr(P, "dish_large_opening_gap_from_main_x_edge"):
    P.dish_large_opening_gap_from_main_x_edge = 12.0
if not hasattr(P, "dish_large_opening_gap_from_main_y_edge"):
    P.dish_large_opening_gap_from_main_y_edge = 12.0

# Four threaded/alignment guide posts on the main-container corners, with matching
# clearance holes cut through the dish.
if not hasattr(P, "enable_corner_dish_guides"):
    P.enable_corner_dish_guides = True
if not hasattr(P, "corner_guide_inset_from_main_edge_x"):
    P.corner_guide_inset_from_main_edge_x = 7.0
if not hasattr(P, "corner_guide_inset_from_main_edge_y"):
    P.corner_guide_inset_from_main_edge_y = 7.0
if not hasattr(P, "corner_guide_core_diameter"):
    P.corner_guide_core_diameter = 2.8
if not hasattr(P, "corner_guide_thread_outer_diameter"):
    P.corner_guide_thread_outer_diameter = 3.6
if not hasattr(P, "corner_guide_hole_clearance"):
    P.corner_guide_hole_clearance = 0.6
if not hasattr(P, "corner_guide_auto_height"):
    P.corner_guide_auto_height = True
if not hasattr(P, "corner_guide_height"):
    P.corner_guide_height = 8.0
if not hasattr(P, "corner_guide_min_thread_above_dish"):
    P.corner_guide_min_thread_above_dish = 3.2
if not hasattr(P, "corner_guide_threaded"):
    P.corner_guide_threaded = True
if not hasattr(P, "corner_guide_thread_pitch"):
    P.corner_guide_thread_pitch = 1.2
if not hasattr(P, "corner_guide_thread_ridge_height"):
    P.corner_guide_thread_ridge_height = 0.30
if not hasattr(P, "corner_guide_unthreaded_base_height"):
    P.corner_guide_unthreaded_base_height = 1.0
if not hasattr(P, "corner_guide_tip_clearance"):
    P.corner_guide_tip_clearance = 0.35
if not hasattr(P, "corner_guide_min_edge_material"):
    P.corner_guide_min_edge_material = 0.8


_effective_dish_outer_length_v29 = effective_dish_outer_length
_effective_dish_outer_width_v29 = effective_dish_outer_width
_make_main_container_v29 = make_main_container
_make_dish_v29 = make_dish
_validate_parameters_v29 = validate_parameters


def dish_outer_gap_x():
    return max(0.0, float(getattr(P, "dish_gap_from_main_x_edge", 3.0)))


def dish_outer_gap_y():
    return max(0.0, float(getattr(P, "dish_gap_from_main_y_edge", 3.0)))


def effective_dish_outer_length():
    """Dish plate length after v30 gap-to-main rule.

    With use_single_large_dish_opening=True, the dish is intentionally smaller
    than the generated main holder by dish_gap_from_main_x_edge on both X ends.
    """
    if bool(getattr(P, "use_single_large_dish_opening", False)):
        return max(1.0, effective_main_outer_length() - 2.0 * dish_outer_gap_x())
    return _effective_dish_outer_length_v29()


def effective_dish_outer_width():
    """Dish plate width after v30 gap-to-main rule."""
    if bool(getattr(P, "use_single_large_dish_opening", False)):
        return max(1.0, effective_main_outer_width() - 2.0 * dish_outer_gap_y())
    return _effective_dish_outer_width_v29()


def dish_large_opening_length():
    """Central dish opening length, controlled from main-container X ends."""
    gap = max(0.0, float(getattr(P, "dish_large_opening_gap_from_main_x_edge", 12.0)))
    return max(0.10, effective_main_outer_length() - 2.0 * gap)


def dish_large_opening_width():
    """Central dish opening width, controlled from main-container Y ends."""
    gap = max(0.0, float(getattr(P, "dish_large_opening_gap_from_main_y_edge", 12.0)))
    return max(0.10, effective_main_outer_width() - 2.0 * gap)


def corner_guides_enabled():
    return bool(getattr(P, "enable_corner_dish_guides", True))


def corner_guide_outer_diameter():
    if bool(getattr(P, "corner_guide_threaded", True)):
        return max(
            float(getattr(P, "corner_guide_core_diameter", 2.8)),
            float(getattr(P, "corner_guide_thread_outer_diameter", 3.6)),
        )
    return float(getattr(P, "corner_guide_core_diameter", 2.8))


def corner_guide_hole_diameter():
    return corner_guide_outer_diameter() + max(0.0, float(getattr(P, "corner_guide_hole_clearance", 0.6)))


def corner_guide_positions():
    """Four corner guide positions, measured inward from main-container edges."""
    L = effective_main_outer_length()
    W = effective_main_outer_width()
    ix = max(0.0, float(getattr(P, "corner_guide_inset_from_main_edge_x", 7.0)))
    iy = max(0.0, float(getattr(P, "corner_guide_inset_from_main_edge_y", 7.0)))
    x_abs = L / 2.0 - ix
    y_abs = W / 2.0 - iy
    return [
        (-x_abs, -y_abs),
        ( x_abs, -y_abs),
        (-x_abs,  y_abs),
        ( x_abs,  y_abs),
    ]


def effective_corner_guide_height():
    h = float(getattr(P, "corner_guide_height", 8.0))
    if bool(getattr(P, "corner_guide_auto_height", True)):
        # Guide starts at the main-container top, passes through the dish, and
        # leaves a short threaded length above the dish for better fixation.
        needed = (
            float(P.z_clearance)
            + float(P.dish_thickness)
            + float(getattr(P, "corner_guide_min_thread_above_dish", 3.2))
        )
        h = max(h, needed)
    return h


def make_corner_guide_shape(zmin, x=0.0, y=0.0):
    """Threaded/bolt-like vertical corner guide fused to the main container."""
    height = effective_corner_guide_height()
    core_d = max(0.2, float(getattr(P, "corner_guide_core_diameter", 2.8)))
    if not bool(getattr(P, "corner_guide_threaded", True)):
        return cylinder_z(core_d, height, zmin, x, y)

    outer_d = corner_guide_outer_diameter()
    shapes = [cylinder_z(core_d, height, zmin, x, y)]

    pitch = max(0.2, float(getattr(P, "corner_guide_thread_pitch", 1.2)))
    ridge_h = max(0.05, min(float(getattr(P, "corner_guide_thread_ridge_height", 0.30)), pitch * 0.75))
    base_h = max(0.0, float(getattr(P, "corner_guide_unthreaded_base_height", 1.0)))
    tip_clear = max(0.0, float(getattr(P, "corner_guide_tip_clearance", 0.35)))

    # Printable pseudo-thread: circular ridges, not a true helical thread. This
    # is usually more robust for small 3D-printed guide/bolt posts.
    z = float(zmin) + base_h + pitch * 0.5
    zmax = float(zmin) + height - tip_clear
    while z + ridge_h / 2.0 <= zmax:
        shapes.append(cylinder_z(outer_d, ridge_h, z - ridge_h / 2.0, x, y))
        z += pitch
    return fuse_many(shapes)


def make_main_container():
    """v30 main container: original body plus four corner guide posts."""
    shape = _make_main_container_v29()
    if corner_guides_enabled():
        guides = [make_corner_guide_shape(effective_main_height(), x, y)
                  for x, y in corner_guide_positions()]
        shape = fuse_many([shape] + guides)
    return safe_fillet(shape, P.fillet_radius)


def make_dish():
    """v30 dish: one large central opening plus matching corner-guide holes.

    If use_single_large_dish_opening=False, the previous four-window dish is used.
    """
    if not bool(getattr(P, "use_single_large_dish_opening", False)):
        return _make_dish_v29()

    plate = box_centered(effective_dish_outer_length(), effective_dish_outer_width(), P.dish_thickness, 0.0)

    if P.enable_dish_handle:
        handle = dish_handle_shape(0.0, P.dish_thickness)
        if handle is not None:
            plate = fuse_many([plate, handle])

    cutters = []

    # One big central opening. It is defined from the main-container outside
    # edges so changing the main-container footprint keeps the dish opening rule
    # consistent.
    cutters.append(box_centered(dish_large_opening_length(),
                                dish_large_opening_width(),
                                P.dish_thickness + 2.0,
                                -1.0, 0.0, 0.0))

    # Clearance holes for the four new corner guides.
    if corner_guides_enabled():
        hole_d = corner_guide_hole_diameter()
        for x, y in corner_guide_positions():
            cutters.append(cylinder_z(hole_d, P.dish_thickness + 2.0, -1.0, x, y))

    # Keep legacy alignment-pin holes if the old system is enabled as well.
    if P.enable_alignment_pins:
        pin_hole_d = alignment_fastener_hole_diameter()
        for x, y in alignment_pin_positions():
            cutters.append(cylinder_z(pin_hole_d, P.dish_thickness + 2.0, -1.0, x, y))

    shape = cut_many(plate, cutters)
    shape = apply_part_label_features(shape, dish_label_shapes())
    shape = safe_fillet(shape, P.fillet_radius)
    return shape


def validate_parameters():
    _validate_parameters_v29()

    if bool(getattr(P, "use_single_large_dish_opening", False)):
        if dish_outer_gap_x() < 0 or dish_outer_gap_y() < 0:
            raise ValueError("dish_gap_from_main_x_edge/y_edge must be non-negative.")
        if effective_dish_outer_length() <= 0 or effective_dish_outer_width() <= 0:
            raise ValueError("Dish outer size became non-positive; reduce dish_gap_from_main_*.")
        if dish_large_opening_length() >= effective_dish_outer_length() - 0.5:
            raise ValueError(
                "The large dish opening is too long for the smaller dish plate. "
                "Increase dish_large_opening_gap_from_main_x_edge or reduce dish_gap_from_main_x_edge."
            )
        if dish_large_opening_width() >= effective_dish_outer_width() - 0.5:
            raise ValueError(
                "The large dish opening is too wide for the smaller dish plate. "
                "Increase dish_large_opening_gap_from_main_y_edge or reduce dish_gap_from_main_y_edge."
            )

    if corner_guides_enabled():
        if corner_guide_hole_diameter() <= 0 or effective_corner_guide_height() <= 0:
            raise ValueError("Corner guide diameter and height must be positive.")
        if float(getattr(P, "corner_guide_thread_pitch", 1.2)) <= 0:
            raise ValueError("corner_guide_thread_pitch must be positive.")

        # Guides must lie under the smaller dish footprint and leave printable
        # material around the dish holes.
        min_edge = max(0.0, float(getattr(P, "corner_guide_min_edge_material", 0.8)))
        required_x_inset = dish_outer_gap_x() + corner_guide_hole_diameter() / 2.0 + min_edge
        required_y_inset = dish_outer_gap_y() + corner_guide_hole_diameter() / 2.0 + min_edge
        if float(getattr(P, "corner_guide_inset_from_main_edge_x", 7.0)) < required_x_inset - 1e-6:
            raise ValueError(
                "corner_guide_inset_from_main_edge_x is too close to the dish edge. "
                f"Use >= {required_x_inset:.2f} mm."
            )
        if float(getattr(P, "corner_guide_inset_from_main_edge_y", 7.0)) < required_y_inset - 1e-6:
            raise ValueError(
                "corner_guide_inset_from_main_edge_y is too close to the dish edge. "
                f"Use >= {required_y_inset:.2f} mm."
            )

        # Guides should remain outside the large central dish opening.
        hole_r = corner_guide_hole_diameter() / 2.0
        open_x_half = dish_large_opening_length() / 2.0
        open_y_half = dish_large_opening_width() / 2.0
        for x, y in corner_guide_positions():
            if abs(x) - hole_r < open_x_half and abs(y) - hole_r < open_y_half:
                raise ValueError(
                    "A corner-guide hole overlaps the large central dish opening. "
                    "Increase dish_large_opening_gap_from_main_x_edge/y_edge or move guides closer to the outer corners."
                )



# -----------------------------------------------------------------------------
# Revision v31 overrides — one large MAIN-container opening, normal four-opening dish
# -----------------------------------------------------------------------------
# Correction to v30:
#   - The dish returns to the original four basket openings/windows.
#   - The MAIN container now gets one large central opening.
#   - The dish remains slightly smaller than the main container by a user-set gap.
#   - Four corner guide/thread posts on the main container are kept, with matching
#     holes cut in the dish.
#   - Only one basket is shown by default.

# Always show one basket by default in the simple assembly view.
P.add_four_basket_copies = False

# v30 used this switch for a single large dish opening. Keep it off in v31.
P.use_single_large_dish_opening = False

if not hasattr(P, "use_single_large_main_opening"):
    P.use_single_large_main_opening = True

# One large central opening in the MAIN container. These gaps are measured from
# the outside edges of the generated main container to the big opening edge.
if not hasattr(P, "main_large_opening_gap_from_main_x_edge"):
    P.main_large_opening_gap_from_main_x_edge = 12.0
if not hasattr(P, "main_large_opening_gap_from_main_y_edge"):
    P.main_large_opening_gap_from_main_y_edge = 12.0

# Dish remains slightly smaller than the main container by these gaps on each side.
# The v30 values are retained if already set; default is 3 mm.
if not hasattr(P, "dish_gap_from_main_x_edge"):
    P.dish_gap_from_main_x_edge = 3.0
if not hasattr(P, "dish_gap_from_main_y_edge"):
    P.dish_gap_from_main_y_edge = 3.0


def main_large_opening_gap_x():
    return max(0.0, float(getattr(P, "main_large_opening_gap_from_main_x_edge", 12.0)))


def main_large_opening_gap_y():
    return max(0.0, float(getattr(P, "main_large_opening_gap_from_main_y_edge", 12.0)))


def main_large_opening_length():
    """One large central opening length in the main container."""
    return max(0.10, effective_main_outer_length() - 2.0 * main_large_opening_gap_x())


def main_large_opening_width():
    """One large central opening width in the main container."""
    return max(0.10, effective_main_outer_width() - 2.0 * main_large_opening_gap_y())


# Override the v30/v29 dish footprint rule. The four-window dish is still used,
# but its outer plate is made slightly smaller than the main container.
def effective_dish_outer_length():
    return max(1.0, effective_main_outer_length() - 2.0 * dish_outer_gap_x())


def effective_dish_outer_width():
    return max(1.0, effective_main_outer_width() - 2.0 * dish_outer_gap_y())


def make_main_container():
    """v31 main container: original holder cut into one big central opening, plus corner guides.

    The original v29 body is used as the starting point so all existing parameters
    for height, wall thickness, modular side slots, labels, and volume marks remain
    available. Then a single large central cut removes the four-opening divider
    structure from the top, leaving one main-container opening controlled by
    main_large_opening_gap_from_main_x_edge/y_edge.
    """
    shape = _make_main_container_v29()

    if bool(getattr(P, "use_single_large_main_opening", True)):
        # Cut from the top down to the closed bottom plane. The bottom remains
        # closed because the cutter starts at P.main_bottom_thickness.
        cutter = box_centered(
            main_large_opening_length(),
            main_large_opening_width(),
            effective_main_height() - float(P.main_bottom_thickness) + 2.0,
            float(P.main_bottom_thickness),
            0.0,
            0.0,
        )
        shape = cut_many(shape, [cutter])

    if corner_guides_enabled():
        guides = [make_corner_guide_shape(effective_main_height(), x, y)
                  for x, y in corner_guide_positions()]
        shape = fuse_many([shape] + guides)

    return safe_fillet(shape, P.fillet_radius)


def make_dish():
    """v31 dish: original four basket openings/windows, plus corner-guide holes.

    This restores the dish behaviour from before v30: four basket openings and
    basket-lip recesses are preserved. The only additions are the smaller outer
    footprint rule and four guide holes matching the main-container corner posts.
    """
    shape = _make_dish_v29()

    cutters = []
    if corner_guides_enabled():
        hole_d = corner_guide_hole_diameter()
        for x, y in corner_guide_positions():
            cutters.append(cylinder_z(hole_d, P.dish_thickness + 2.0, -1.0, x, y))

    if cutters:
        shape = cut_many(shape, cutters)
    return safe_fillet(shape, P.fillet_radius)


def validate_parameters():
    """v31 validation."""
    _validate_parameters_v29()

    if bool(getattr(P, "use_single_large_main_opening", True)):
        if main_large_opening_gap_x() <= 0 or main_large_opening_gap_y() <= 0:
            raise ValueError("main_large_opening_gap_from_main_x_edge/y_edge must be positive.")
        if main_large_opening_length() >= effective_main_outer_length() - 0.5:
            raise ValueError("Main large opening is too long; increase main_large_opening_gap_from_main_x_edge.")
        if main_large_opening_width() >= effective_main_outer_width() - 0.5:
            raise ValueError("Main large opening is too wide; increase main_large_opening_gap_from_main_y_edge.")

    # The dish is smaller than the main holder, but must still fit the four dish
    # basket windows/lip recesses generated by the original dish logic.
    if effective_dish_outer_length() <= 0 or effective_dish_outer_width() <= 0:
        raise ValueError("Dish outer size became non-positive; reduce dish_gap_from_main_*.")

    # Corner guides must lie under the smaller dish footprint, leave printable
    # material around the dish holes, and stay outside the big main opening.
    if corner_guides_enabled():
        if corner_guide_hole_diameter() <= 0 or effective_corner_guide_height() <= 0:
            raise ValueError("Corner guide diameter and height must be positive.")
        if bool(getattr(P, "corner_guide_threaded", True)) and float(getattr(P, "corner_guide_thread_pitch", 1.2)) <= 0:
            raise ValueError("corner_guide_thread_pitch must be positive.")

        min_edge = max(0.0, float(getattr(P, "corner_guide_min_edge_material", 0.8)))
        required_x_inset = dish_outer_gap_x() + corner_guide_hole_diameter() / 2.0 + min_edge
        required_y_inset = dish_outer_gap_y() + corner_guide_hole_diameter() / 2.0 + min_edge
        if float(getattr(P, "corner_guide_inset_from_main_edge_x", 7.0)) < required_x_inset - 1e-6:
            raise ValueError(
                "corner_guide_inset_from_main_edge_x is too close to the smaller dish edge. "
                f"Use >= {required_x_inset:.2f} mm."
            )
        if float(getattr(P, "corner_guide_inset_from_main_edge_y", 7.0)) < required_y_inset - 1e-6:
            raise ValueError(
                "corner_guide_inset_from_main_edge_y is too close to the smaller dish edge. "
                f"Use >= {required_y_inset:.2f} mm."
            )

        post_r = corner_guide_outer_diameter() / 2.0
        open_x_half = main_large_opening_length() / 2.0
        open_y_half = main_large_opening_width() / 2.0
        for x, y in corner_guide_positions():
            if abs(x) - post_r < open_x_half and abs(y) - post_r < open_y_half:
                raise ValueError(
                    "A corner guide overlaps the large main opening. Increase "
                    "main_large_opening_gap_from_main_x_edge/y_edge or move the guides closer to the outer corners."
                )



# -----------------------------------------------------------------------------
# Revision v33 overrides — square central dish opening with shallow recess
# -----------------------------------------------------------------------------
# Keeps the user's latest v31 parameters and behaviour:
#   - Main container has one large central opening.
#   - Dish keeps four basket openings.
#   - Only one basket is shown by default.
# This revision keeps the square-opening parameters visible inside class P and replaces the dish's circular central fill/access hole with
# a 15 x 15 mm square through-opening and a shallow square counterbore/recess.

if not hasattr(P, "use_square_dish_central_opening"):
    P.use_square_dish_central_opening = True

# Through-opening size in the dish centre.
if not hasattr(P, "dish_central_square_opening_length"):
    P.dish_central_square_opening_length = 15.0
if not hasattr(P, "dish_central_square_opening_width"):
    P.dish_central_square_opening_width = 15.0

# Recess/counterbore around the square opening. The recess is larger than the
# through-hole by 0.5 mm on each side by default, and is cut down from the top of
# the dish so a matching square feature can sit inside the dish surface.
if not hasattr(P, "enable_dish_central_square_recess"):
    P.enable_dish_central_square_recess = True
if not hasattr(P, "dish_central_square_recess_side_clearance"):
    P.dish_central_square_recess_side_clearance = 0.5
if not hasattr(P, "dish_central_square_recess_depth"):
    P.dish_central_square_recess_depth = 1.0

# Disable the old round central fill hole by default when the square opening is used.
# The square opening below replaces it.
if bool(getattr(P, "use_square_dish_central_opening", True)):
    P.enable_dish_central_fill_hole = False


_validate_parameters_v31 = validate_parameters


def dish_central_square_opening_length():
    return max(0.10, float(getattr(P, "dish_central_square_opening_length", 15.0)))


def dish_central_square_opening_width():
    return max(0.10, float(getattr(P, "dish_central_square_opening_width", 15.0)))


def dish_central_square_recess_clearance():
    return max(0.0, float(getattr(P, "dish_central_square_recess_side_clearance", 0.5)))


def dish_central_square_recess_depth():
    if not bool(getattr(P, "enable_dish_central_square_recess", True)):
        return 0.0
    return max(0.0, float(getattr(P, "dish_central_square_recess_depth", 1.0)))


def dish_central_square_recess_length():
    return dish_central_square_opening_length() + 2.0 * dish_central_square_recess_clearance()


def dish_central_square_recess_width():
    return dish_central_square_opening_width() + 2.0 * dish_central_square_recess_clearance()


def make_dish():
    """v33 dish: four basket windows plus square central opening/recess.

    The old circular dish_central_fill_hole is suppressed. A 15 x 15 mm square
    through-opening is cut in the centre. Around it, a larger shallow square
    recess is cut from the top of the dish. The recess defaults to 0.5 mm extra
    on each side and 1.0 mm depth.
    """
    # Build the original four-window dish, but force the old circular centre hole
    # off while it is being created. Then add the new square centre features.
    old_centre_hole_state = getattr(P, "enable_dish_central_fill_hole", False)
    if bool(getattr(P, "use_square_dish_central_opening", True)):
        P.enable_dish_central_fill_hole = False
    try:
        shape = _make_dish_v29()
    finally:
        P.enable_dish_central_fill_hole = old_centre_hole_state

    cutters = []

    if bool(getattr(P, "use_square_dish_central_opening", True)):
        # Through square hole.
        cutters.append(box_centered(
            dish_central_square_opening_length(),
            dish_central_square_opening_width(),
            float(P.dish_thickness) + 2.0,
            -1.0,
            0.0,
            0.0,
        ))

        # Shallow top-side recess/counterbore around the square hole.
        recess_depth = dish_central_square_recess_depth()
        if recess_depth > 0:
            cutters.append(box_centered(
                dish_central_square_recess_length(),
                dish_central_square_recess_width(),
                recess_depth + 0.08,
                float(P.dish_thickness) - recess_depth,
                0.0,
                0.0,
            ))

    # Keep v31 corner-guide holes in the dish.
    if corner_guides_enabled():
        hole_d = corner_guide_hole_diameter()
        for x, y in corner_guide_positions():
            cutters.append(cylinder_z(hole_d, float(P.dish_thickness) + 2.0, -1.0, x, y))

    if cutters:
        shape = cut_many(shape, cutters)
    return safe_fillet(shape, P.fillet_radius)


def validate_parameters():
    _validate_parameters_v31()

    if bool(getattr(P, "use_square_dish_central_opening", True)):
        if dish_central_square_opening_length() <= 0 or dish_central_square_opening_width() <= 0:
            raise ValueError("dish_central_square_opening_length/width must be positive.")
        if dish_central_square_recess_depth() >= float(P.dish_thickness) - 0.05:
            raise ValueError("dish_central_square_recess_depth must be smaller than dish_thickness.")
        if dish_central_square_recess_length() >= effective_dish_outer_length() - 0.5:
            raise ValueError("Central square recess is too long for the dish plate.")
        if dish_central_square_recess_width() >= effective_dish_outer_width() - 0.5:
            raise ValueError("Central square recess is too wide for the dish plate.")

        # Check that the central square recess does not overlap the four basket
        # through-windows. This is intentionally conservative and based on the
        # axis-aligned bounding boxes of the features.
        recess_half_x = dish_central_square_recess_length() / 2.0
        recess_half_y = dish_central_square_recess_width() / 2.0
        win_half_x = dish_window_length() / 2.0
        win_half_y = dish_window_width() / 2.0
        for x, y in opening_centres():
            overlap_x = abs(x) < (recess_half_x + win_half_x)
            overlap_y = abs(y) < (recess_half_y + win_half_y)
            if overlap_x and overlap_y:
                raise ValueError(
                    "The 15 mm central square recess/opening overlaps a basket window. "
                    "Increase opening_gap_x/opening_gap_y or reduce the central square size/recess."
                )



# -----------------------------------------------------------------------------
# Revision v34 overrides — acrylic-window guide trial around one dish opening
# -----------------------------------------------------------------------------
# Adds a shallow rectangular groove plus raised guide rails around selected dish
# basket opening(s) for 2 mm acrylic sheet. The small central square opening is
# intentionally untouched. Defaults apply the feature to opening 1 only.

_make_dish_v33 = make_dish
_validate_parameters_v33 = validate_parameters
_create_document_v33 = create_document


def acrylic_window_guides_enabled():
    return bool(getattr(P, "enable_acrylic_window_guides", False))


def acrylic_window_indices():
    raw = getattr(P, "acrylic_window_opening_indices", (1,))
    if isinstance(raw, int):
        raw = (raw,)
    if isinstance(raw, str):
        raw = raw.replace(",", " ").split()
    out = []
    for item in raw:
        try:
            idx = int(item)
        except Exception:
            continue
        if 1 <= idx <= 4 and idx not in out:
            out.append(idx)
    return out or [1]


def acrylic_sheet_thickness():
    return max(0.10, float(getattr(P, "acrylic_sheet_thickness", 2.0)))


def acrylic_sheet_slot_width():
    return acrylic_sheet_thickness() + max(0.0, float(getattr(P, "acrylic_sheet_slot_clearance", 0.30)))


def acrylic_window_slot_depth():
    return max(0.0, float(getattr(P, "acrylic_window_slot_depth", 1.0)))


def acrylic_window_guide_height():
    return max(0.0, float(getattr(P, "acrylic_window_guide_height", 3.0)))


def acrylic_window_guide_rail_width():
    return max(0.05, float(getattr(P, "acrylic_window_guide_rail_width", 1.0)))


def acrylic_window_clearance_from_basket_recess():
    return max(0.0, float(getattr(P, "acrylic_window_clearance_from_basket_recess", 0.8)))


def acrylic_window_corner_overlap():
    return max(0.0, float(getattr(P, "acrylic_window_corner_overlap", 3.0)))


def acrylic_window_sheet_preview_enabled():
    return bool(getattr(P, "show_acrylic_window_sheet_preview", True))


def acrylic_window_sheet_preview_height():
    return max(0.5, float(getattr(P, "acrylic_window_sheet_preview_height", 16.0)))


def acrylic_window_seat_length():
    """Use the basket-lip recess footprint, not the smaller through-window.

    This keeps the acrylic guide outside the basket seat so it should not block
    the basket lip from sitting in the dish recess.
    """
    return effective_basket_lip_length() + float(P.dish_basket_lip_recess_clearance)


def acrylic_window_seat_width():
    return effective_basket_lip_width() + float(P.dish_basket_lip_recess_clearance)


def _acrylic_window_side_geometry(x, y, include_preview=False):
    """Return (cutters, rails_or_preview) for one opening centre.

    Geometry is in the dish's local coordinate system: the dish top is at
    z=P.dish_thickness. Each side has a shallow groove cut into the top surface,
    plus two raised rails that create a slot for nominal 2 mm acrylic sheet.
    """
    seat_l = acrylic_window_seat_length()
    seat_w = acrylic_window_seat_width()
    slot_w = acrylic_sheet_slot_width()
    sheet_t = acrylic_sheet_thickness()
    slot_depth = acrylic_window_slot_depth()
    rail_w = acrylic_window_guide_rail_width()
    rail_h = acrylic_window_guide_height()
    gap = acrylic_window_clearance_from_basket_recess()
    corner_ov = acrylic_window_corner_overlap()

    cutters = []
    solids = []
    z_top = float(P.dish_thickness)
    z_slot = z_top - slot_depth
    base_overlap = min(0.20, max(0.0, rail_h) * 0.20)
    rail_z = z_top - base_overlap
    rail_height = rail_h + base_overlap
    side_len_x = seat_l + 2.0 * corner_ov
    side_len_y = seat_w + 2.0 * corner_ov

    # ±X sides: channels run parallel to Y.
    for sign in (-1.0, 1.0):
        edge_x = x + sign * seat_l / 2.0
        inner_rail_x = edge_x + sign * (gap + rail_w / 2.0)
        slot_x = edge_x + sign * (gap + rail_w + slot_w / 2.0)
        outer_rail_x = edge_x + sign * (gap + rail_w + slot_w + rail_w / 2.0)

        if include_preview:
            solids.append(box_centered(sheet_t, side_len_y, acrylic_window_sheet_preview_height(),
                                       z_top - slot_depth, slot_x, y))
        else:
            if slot_depth > 0:
                cutters.append(box_centered(slot_w, side_len_y, slot_depth + 0.08,
                                            z_slot, slot_x, y))
            if rail_h > 0:
                solids.append(box_centered(rail_w, side_len_y, rail_height,
                                           rail_z, inner_rail_x, y))
                solids.append(box_centered(rail_w, side_len_y, rail_height,
                                           rail_z, outer_rail_x, y))

    # ±Y sides: channels run parallel to X.
    for sign in (-1.0, 1.0):
        edge_y = y + sign * seat_w / 2.0
        inner_rail_y = edge_y + sign * (gap + rail_w / 2.0)
        slot_y = edge_y + sign * (gap + rail_w + slot_w / 2.0)
        outer_rail_y = edge_y + sign * (gap + rail_w + slot_w + rail_w / 2.0)

        if include_preview:
            solids.append(box_centered(side_len_x, sheet_t, acrylic_window_sheet_preview_height(),
                                       z_top - slot_depth, x, slot_y))
        else:
            if slot_depth > 0:
                cutters.append(box_centered(side_len_x, slot_w, slot_depth + 0.08,
                                            z_slot, x, slot_y))
            if rail_h > 0:
                solids.append(box_centered(side_len_x, rail_w, rail_height,
                                           rail_z, x, inner_rail_y))
                solids.append(box_centered(side_len_x, rail_w, rail_height,
                                           rail_z, x, outer_rail_y))

    return cutters, solids


def acrylic_window_guide_shapes():
    cutters = []
    rails = []
    centres = opening_centres()
    for idx in acrylic_window_indices():
        x, y = centres[idx - 1]
        c, r = _acrylic_window_side_geometry(x, y, include_preview=False)
        cutters.extend(c)
        rails.extend(r)
    return cutters, rails


def make_acrylic_window_preview_shape():
    preview_shapes = []
    centres = opening_centres()
    for idx in acrylic_window_indices():
        x, y = centres[idx - 1]
        _, sheets = _acrylic_window_side_geometry(x, y, include_preview=True)
        preview_shapes.extend(sheets)
    if not preview_shapes:
        return None
    return fuse_many(preview_shapes)


def make_dish():
    """v34 dish: v33 dish plus acrylic-sheet guide trial around one opening."""
    shape = _make_dish_v33()
    if not acrylic_window_guides_enabled():
        return shape

    cutters, rails = acrylic_window_guide_shapes()
    if cutters:
        shape = cut_many(shape, cutters)
    if rails:
        shape = fuse_many([shape] + rails)
    return safe_fillet(shape, P.fillet_radius)


def validate_parameters():
    _validate_parameters_v33()
    if not acrylic_window_guides_enabled():
        return

    if not acrylic_window_indices():
        raise ValueError("acrylic_window_opening_indices must contain at least one index from 1 to 4.")
    if acrylic_sheet_thickness() <= 0:
        raise ValueError("acrylic_sheet_thickness must be positive.")
    if acrylic_sheet_slot_width() <= acrylic_sheet_thickness() - 1e-6:
        raise ValueError("acrylic_sheet_slot_clearance must not make the slot smaller than the sheet.")
    if acrylic_window_slot_depth() >= float(P.dish_thickness) - 0.05:
        raise ValueError("acrylic_window_slot_depth must be smaller than dish_thickness.")
    if acrylic_window_guide_height() <= 0 and acrylic_window_slot_depth() <= 0:
        raise ValueError("Use either a positive acrylic_window_guide_height or a positive acrylic_window_slot_depth.")

    # Check that the guide footprint remains on the dish plate.
    seat_l = acrylic_window_seat_length()
    seat_w = acrylic_window_seat_width()
    total_out_x = seat_l / 2.0 + acrylic_window_clearance_from_basket_recess() + 2.0 * acrylic_window_guide_rail_width() + acrylic_sheet_slot_width()
    total_out_y = seat_w / 2.0 + acrylic_window_clearance_from_basket_recess() + 2.0 * acrylic_window_guide_rail_width() + acrylic_sheet_slot_width()
    dish_half_l = effective_dish_outer_length() / 2.0
    dish_half_w = effective_dish_outer_width() / 2.0
    for idx in acrylic_window_indices():
        x, y = opening_centres()[idx - 1]
        if abs(x) + total_out_x > dish_half_l + 1e-6:
            raise ValueError(
                "Acrylic guide for opening %d exceeds the dish length. Reduce acrylic_window_clearance_from_basket_recess, "
                "rail/slot width, or increase dish size." % idx
            )
        if abs(y) + total_out_y > dish_half_w + 1e-6:
            raise ValueError(
                "Acrylic guide for opening %d exceeds the dish width. Reduce acrylic_window_clearance_from_basket_recess, "
                "rail/slot width, or increase dish size." % idx
            )


def create_document():
    """Create the normal assembly and optionally add transparent acrylic previews."""
    doc = _create_document_v33()
    if acrylic_window_guides_enabled() and acrylic_window_sheet_preview_enabled():
        preview = make_acrylic_window_preview_shape()
        if preview is not None:
            dish_z = main_dish_support_z() + float(P.z_clearance)
            add_feature(
                doc,
                "Acrylic_Window_Preview_Opening_%s" % "_".join(str(i) for i in acrylic_window_indices()),
                preview,
                App.Placement(App.Vector(0, 0, dish_z), App.Rotation()),
                color=(0.65, 0.90, 1.00),
                transparency=65,
            )
            doc.recompute()
    return doc



# -----------------------------------------------------------------------------
# Revision v35 overrides — upright U-channels for acrylic sheets around one opening
# -----------------------------------------------------------------------------
# This replaces the v34 rail/groove trial with the clarified design:
#   - A separate U-channel is placed along each of the four sides of a selected
#     dish basket opening.
#   - The empty internal gap of the U-channel is user-controlled; default 2.2 mm
#     for a nominal 2.0 mm acrylic sheet.
#   - Horizontal holes are cut through the U-channel walls and the acrylic-sheet
#     path so the user can drill matching holes in the acrylic and pin/screw it.
#   - The small central square opening is not touched.
#   - Defaults apply to opening 1 only for a first test.


def acrylic_u_channels_enabled():
    return bool(getattr(P, "enable_acrylic_u_channels", True))


def acrylic_u_channel_indices():
    raw = getattr(P, "acrylic_u_channel_opening_indices", (1,))
    if isinstance(raw, int):
        raw = (raw,)
    if isinstance(raw, str):
        raw = raw.replace(",", " ").split()
    out = []
    for item in raw:
        try:
            idx = int(item)
        except Exception:
            continue
        if 1 <= idx <= 4 and idx not in out:
            out.append(idx)
    return out or [1]


def acrylic_u_sheet_thickness():
    return max(0.10, float(getattr(P, "acrylic_sheet_thickness", 2.0)))


def acrylic_u_inner_gap():
    return max(0.10, float(getattr(P, "acrylic_u_channel_inner_gap", 2.2)))


def acrylic_u_wall_thickness():
    return max(0.20, float(getattr(P, "acrylic_u_channel_wall_thickness", 1.2)))


def acrylic_u_channel_height():
    return max(0.20, float(getattr(P, "acrylic_u_channel_height", 5.0)))


def acrylic_u_base_groove_depth():
    return max(0.0, float(getattr(P, "acrylic_u_channel_base_groove_depth", 0.5)))


def acrylic_u_clearance_from_basket_recess():
    return max(0.0, float(getattr(P, "acrylic_u_channel_clearance_from_basket_recess", 0.8)))


def acrylic_u_corner_overlap():
    return max(0.0, float(getattr(P, "acrylic_u_channel_corner_overlap", 3.0)))


def acrylic_u_holes_per_side():
    return max(0, int(getattr(P, "acrylic_u_channel_holes_per_side", 2)))


def acrylic_u_hole_diameter():
    return max(0.0, float(getattr(P, "acrylic_u_channel_hole_diameter", 1.6)))


def acrylic_u_hole_height_above_dish():
    return max(0.0, float(getattr(P, "acrylic_u_channel_hole_height_above_dish", 2.7)))


def acrylic_u_hole_end_margin():
    return max(0.0, float(getattr(P, "acrylic_u_channel_hole_end_margin", 5.0)))


def acrylic_u_hole_extra_length():
    return max(0.0, float(getattr(P, "acrylic_u_channel_hole_extra_length", 1.0)))


def acrylic_u_preview_enabled():
    return bool(getattr(P, "show_acrylic_u_sheet_preview", True))


def acrylic_u_preview_height():
    return max(0.5, float(getattr(P, "acrylic_u_sheet_preview_height", 18.0)))


def acrylic_u_seat_length():
    """Use the basket-lip recess footprint as the protected opening footprint."""
    return effective_basket_lip_length() + float(P.dish_basket_lip_recess_clearance)


def acrylic_u_seat_width():
    return effective_basket_lip_width() + float(P.dish_basket_lip_recess_clearance)


def _positions_along_channel(length, count, end_margin):
    """Hole offsets along one U-channel side, centred and avoiding the ends."""
    count = max(0, int(count))
    if count <= 0:
        return []
    length = max(0.0, float(length))
    end_margin = max(0.0, float(end_margin))
    usable = max(0.0, length - 2.0 * end_margin)
    if count == 1 or usable <= 0.01:
        return [0.0]
    return [(-usable / 2.0 + i * usable / float(count - 1)) for i in range(count)]


def _acrylic_u_channel_geometry_for_opening(x, y, include_preview=False):
    """Return (dish_cutters, solids, hole_cutters, preview_sheets) for one opening.

    Local dish coordinates are used. The dish top surface is z=P.dish_thickness.
    For each side of the selected opening, two raised walls form a U-channel.
    The empty gap between those walls is acrylic_u_channel_inner_gap.
    """
    seat_l = acrylic_u_seat_length()
    seat_w = acrylic_u_seat_width()
    gap = acrylic_u_inner_gap()
    wall = acrylic_u_wall_thickness()
    height = acrylic_u_channel_height()
    groove_depth = acrylic_u_base_groove_depth()
    clearance = acrylic_u_clearance_from_basket_recess()
    corner_ov = acrylic_u_corner_overlap()
    hole_d = acrylic_u_hole_diameter()
    hole_count = acrylic_u_holes_per_side()
    hole_extra = acrylic_u_hole_extra_length()

    z_top = float(P.dish_thickness)
    base_overlap = min(0.20, height * 0.15)
    wall_z = z_top - base_overlap
    wall_h = height + base_overlap
    groove_z = z_top - groove_depth
    hole_z = z_top + acrylic_u_hole_height_above_dish()

    # The U-channel length extends beyond the basket-lip recess so the side
    # brackets visually meet/overlap near the corners.
    side_len_x = seat_l + 2.0 * corner_ov  # used by N/S channels, length along X
    side_len_y = seat_w + 2.0 * corner_ov  # used by E/W channels, length along Y

    dish_cutters = []
    solids = []
    hole_cutters = []
    preview_sheets = []

    # ±X sides: U-channel runs along Y, sheet lies in a vertical Y-Z plane.
    for sign in (-1.0, 1.0):
        edge_x = x + sign * seat_l / 2.0
        inner_wall_x = edge_x + sign * (clearance + wall / 2.0)
        slot_x = edge_x + sign * (clearance + wall + gap / 2.0)
        outer_wall_x = edge_x + sign * (clearance + wall + gap + wall / 2.0)

        if groove_depth > 0:
            dish_cutters.append(box_centered(gap, side_len_y, groove_depth + 0.08,
                                             groove_z, slot_x, y))

        solids.append(box_centered(wall, side_len_y, wall_h, wall_z, inner_wall_x, y))
        solids.append(box_centered(wall, side_len_y, wall_h, wall_z, outer_wall_x, y))

        if include_preview:
            sheet_t = min(acrylic_u_sheet_thickness(), gap)
            preview_sheets.append(box_centered(sheet_t, side_len_y, acrylic_u_preview_height() + groove_depth,
                                               z_top - groove_depth, slot_x, y))

        if hole_count > 0 and hole_d > 0:
            hole_len = 2.0 * wall + gap + 2.0 * hole_extra
            for off in _positions_along_channel(side_len_y, hole_count, acrylic_u_hole_end_margin()):
                hole_cutters.append(cylinder_x(hole_d, hole_len, hole_z, slot_x, y + off))

    # ±Y sides: U-channel runs along X, sheet lies in a vertical X-Z plane.
    for sign in (-1.0, 1.0):
        edge_y = y + sign * seat_w / 2.0
        inner_wall_y = edge_y + sign * (clearance + wall / 2.0)
        slot_y = edge_y + sign * (clearance + wall + gap / 2.0)
        outer_wall_y = edge_y + sign * (clearance + wall + gap + wall / 2.0)

        if groove_depth > 0:
            dish_cutters.append(box_centered(side_len_x, gap, groove_depth + 0.08,
                                             groove_z, x, slot_y))

        solids.append(box_centered(side_len_x, wall, wall_h, wall_z, x, inner_wall_y))
        solids.append(box_centered(side_len_x, wall, wall_h, wall_z, x, outer_wall_y))

        if include_preview:
            sheet_t = min(acrylic_u_sheet_thickness(), gap)
            preview_sheets.append(box_centered(side_len_x, sheet_t, acrylic_u_preview_height() + groove_depth,
                                               z_top - groove_depth, x, slot_y))

        if hole_count > 0 and hole_d > 0:
            hole_len = 2.0 * wall + gap + 2.0 * hole_extra
            for off in _positions_along_channel(side_len_x, hole_count, acrylic_u_hole_end_margin()):
                hole_cutters.append(cylinder_y(hole_d, hole_len, hole_z, x + off, slot_y))

    return dish_cutters, solids, hole_cutters, preview_sheets


def acrylic_u_channel_shapes():
    dish_cutters = []
    solids = []
    hole_cutters = []
    centres = opening_centres()
    for idx in acrylic_u_channel_indices():
        x, y = centres[idx - 1]
        c, s, h, _ = _acrylic_u_channel_geometry_for_opening(x, y, include_preview=False)
        dish_cutters.extend(c)
        solids.extend(s)
        hole_cutters.extend(h)
    return dish_cutters, solids, hole_cutters


def make_acrylic_u_sheet_preview_shape():
    preview_sheets = []
    hole_cutters = []
    centres = opening_centres()
    for idx in acrylic_u_channel_indices():
        x, y = centres[idx - 1]
        _, _, h, p = _acrylic_u_channel_geometry_for_opening(x, y, include_preview=True)
        hole_cutters.extend(h)
        preview_sheets.extend(p)
    if not preview_sheets:
        return None
    preview = fuse_many(preview_sheets)
    if hole_cutters:
        preview = cut_many(preview, hole_cutters)
    return safe_remove_splitter(preview)


def make_dish():
    """v35 dish: v33 dish plus U-channel acrylic holders around selected opening(s)."""
    # Use the v33 dish as the base. This avoids the earlier v34 simple rail trial.
    shape = _make_dish_v33()
    if not acrylic_u_channels_enabled():
        return shape

    dish_cutters, solids, hole_cutters = acrylic_u_channel_shapes()
    if dish_cutters:
        shape = cut_many(shape, dish_cutters)
    if solids:
        shape = fuse_many([shape] + solids)
    if hole_cutters:
        shape = cut_many(shape, hole_cutters)
    return safe_fillet(shape, P.fillet_radius)


def validate_parameters():
    _validate_parameters_v33()
    if not acrylic_u_channels_enabled():
        return

    if not acrylic_u_channel_indices():
        raise ValueError("acrylic_u_channel_opening_indices must contain at least one index from 1 to 4.")
    if acrylic_u_inner_gap() < acrylic_u_sheet_thickness() - 1e-6:
        raise ValueError(
            "acrylic_u_channel_inner_gap is smaller than acrylic_sheet_thickness. "
            "Use about 2.1-2.2 mm for a 2.0 mm sheet."
        )
    if acrylic_u_base_groove_depth() >= float(P.dish_thickness) - 0.05:
        raise ValueError("acrylic_u_channel_base_groove_depth must be smaller than dish_thickness.")
    if acrylic_u_hole_diameter() > 0:
        if acrylic_u_hole_height_above_dish() <= acrylic_u_hole_diameter() / 2.0:
            raise ValueError("acrylic_u_channel_hole_height_above_dish is too low; the hole may cut into the dish top.")
        if acrylic_u_hole_height_above_dish() >= acrylic_u_channel_height() - acrylic_u_hole_diameter() / 2.0:
            raise ValueError("acrylic_u_channel_hole_height_above_dish is too high for the U-channel wall height.")

    seat_l = acrylic_u_seat_length()
    seat_w = acrylic_u_seat_width()
    out_x = seat_l / 2.0 + acrylic_u_clearance_from_basket_recess() + 2.0 * acrylic_u_wall_thickness() + acrylic_u_inner_gap()
    out_y = seat_w / 2.0 + acrylic_u_clearance_from_basket_recess() + 2.0 * acrylic_u_wall_thickness() + acrylic_u_inner_gap()
    ext_x = max(out_x, seat_l / 2.0 + acrylic_u_corner_overlap())
    ext_y = max(out_y, seat_w / 2.0 + acrylic_u_corner_overlap())
    dish_half_l = effective_dish_outer_length() / 2.0
    dish_half_w = effective_dish_outer_width() / 2.0
    for idx in acrylic_u_channel_indices():
        x, y = opening_centres()[idx - 1]
        if abs(x) + ext_x > dish_half_l + 1e-6:
            raise ValueError(
                "Acrylic U-channel for opening %d exceeds the dish length. Reduce wall/gap/clearance/corner overlap "
                "or increase dish size." % idx
            )
        if abs(y) + ext_y > dish_half_w + 1e-6:
            raise ValueError(
                "Acrylic U-channel for opening %d exceeds the dish width. Reduce wall/gap/clearance/corner overlap "
                "or increase dish size." % idx
            )


def create_document():
    """Create the assembly and optionally add transparent acrylic-sheet previews."""
    doc = _create_document_v33()
    if acrylic_u_channels_enabled() and acrylic_u_preview_enabled():
        preview = make_acrylic_u_sheet_preview_shape()
        if preview is not None:
            dish_z = main_dish_support_z() + float(P.z_clearance)
            add_feature(
                doc,
                "Acrylic_U_Channel_Sheet_Preview_Opening_%s" % "_".join(str(i) for i in acrylic_u_channel_indices()),
                preview,
                App.Placement(App.Vector(0, 0, dish_z), App.Rotation()),
                color=(0.65, 0.90, 1.00),
                transparency=65,
            )
            doc.recompute()
    return doc



# -----------------------------------------------------------------------------
# Revision v36 overrides — simple two U-clips on one long side; dish-only view
# -----------------------------------------------------------------------------
# This simplifies the acrylic holder idea:
#   - Only two short U-shaped clips are added.
#   - They are placed on one long side of one selected dish basket opening.
#   - Each clip is 10 mm long by default.
#   - The two U walls are fused into the dish; they are not separate parts.
#   - Only the dish is shown in the FreeCAD document.

# Force older acrylic experiments off in this revision.
P.enable_acrylic_u_channels = False
P.enable_acrylic_window_guides = False
P.show_acrylic_u_sheet_preview = False
P.show_acrylic_window_sheet_preview = False


def simple_acrylic_u_clips_enabled():
    return bool(getattr(P, "enable_simple_acrylic_u_clips", True))


def simple_acrylic_u_clip_opening_index():
    idx = int(getattr(P, "simple_acrylic_u_clip_opening_index", 1))
    return max(1, min(4, idx))


def simple_acrylic_u_clip_side():
    return str(getattr(P, "simple_acrylic_u_clip_side", "outer_long_side")).strip().lower()


def simple_acrylic_u_clip_count():
    return max(1, int(getattr(P, "simple_acrylic_u_clip_count", 2)))


def simple_acrylic_u_clip_length():
    return max(0.5, float(getattr(P, "simple_acrylic_u_clip_length", 10.0)))


def simple_acrylic_u_clip_offset_from_center(seat_length):
    manual = float(getattr(P, "simple_acrylic_u_clip_offset_from_center", 0.0))
    if manual > 0:
        return manual
    # Default: place two clips symmetrically at about quarter-span positions.
    # For a ~38 mm long basket recess, this gives about +/-9.5 mm centres.
    return max(0.0, float(seat_length) * 0.25)


def simple_acrylic_u_inner_gap():
    return max(0.10, float(getattr(P, "simple_acrylic_u_clip_inner_gap", 2.2)))


def simple_acrylic_u_wall_thickness():
    return max(0.20, float(getattr(P, "simple_acrylic_u_clip_wall_thickness", 1.2)))


def simple_acrylic_u_height():
    return max(0.20, float(getattr(P, "simple_acrylic_u_clip_height", 5.0)))


def simple_acrylic_u_base_groove_depth():
    return max(0.0, float(getattr(P, "simple_acrylic_u_clip_base_groove_depth", 0.3)))


def simple_acrylic_u_clearance_from_basket_recess():
    return max(0.0, float(getattr(P, "simple_acrylic_u_clip_clearance_from_basket_recess", 0.8)))


def simple_acrylic_u_seat_length():
    # Use the basket-lip recess footprint so the clips sit outside the basket seat.
    return effective_basket_lip_length() + float(P.dish_basket_lip_recess_clearance)


def simple_acrylic_u_seat_width():
    return effective_basket_lip_width() + float(P.dish_basket_lip_recess_clearance)


def _simple_acrylic_long_side_sign(opening_y):
    """Choose which long side gets the clips.

    For opening 1 by default, 'outer_long_side' places the clips on the lower
    outside long edge. This keeps the trial visually clear and away from the
    central square opening.
    """
    side = simple_acrylic_u_clip_side()
    if side in {"positive_y", "+y", "upper", "north", "back"}:
        return 1.0
    if side in {"negative_y", "-y", "lower", "south", "front"}:
        return -1.0
    if side in {"inner_long_side", "inner", "toward_center", "towards_center"}:
        return -1.0 if float(opening_y) > 0 else 1.0
    # Default: outer side, away from dish centre.
    return 1.0 if float(opening_y) >= 0 else -1.0


def simple_acrylic_u_clip_shapes_for_opening(x, y):
    """Return (dish_cutters, solids) for two short U-clips on one long side.

    The long side of the basket opening runs along X. Each U-clip therefore runs
    along X and grips an acrylic sheet whose thickness lies in Y. The two raised
    walls are fused into the dish. The shallow groove is optional and only seats
    the acrylic edge slightly into the dish.
    """
    seat_l = simple_acrylic_u_seat_length()
    seat_w = simple_acrylic_u_seat_width()
    sign = _simple_acrylic_long_side_sign(y)

    clip_count = simple_acrylic_u_clip_count()
    clip_len = simple_acrylic_u_clip_length()
    offset = simple_acrylic_u_clip_offset_from_center(seat_l)
    gap = simple_acrylic_u_inner_gap()
    wall = simple_acrylic_u_wall_thickness()
    height = simple_acrylic_u_height()
    clearance = simple_acrylic_u_clearance_from_basket_recess()
    groove_depth = simple_acrylic_u_base_groove_depth()

    z_top = float(P.dish_thickness)
    base_overlap = min(0.20, height * 0.15)
    wall_z = z_top - base_overlap
    wall_h = height + base_overlap
    groove_z = z_top - groove_depth

    # One long side of the basket-lip recess.
    edge_y = y + sign * seat_w / 2.0
    inner_wall_y = edge_y + sign * (clearance + wall / 2.0)
    slot_y = edge_y + sign * (clearance + wall + gap / 2.0)
    outer_wall_y = edge_y + sign * (clearance + wall + gap + wall / 2.0)

    if clip_count == 1:
        centres_x = [x]
    elif clip_count == 2:
        centres_x = [x - offset, x + offset]
    else:
        # General fallback: distribute clips along the long side while keeping
        # them within the basket-recess span.
        usable = max(0.0, seat_l - clip_len)
        span = min(usable, 2.0 * offset)
        centres_x = [x - span / 2.0 + i * span / float(clip_count - 1) for i in range(clip_count)]

    dish_cutters = []
    solids = []
    for cx in centres_x:
        if groove_depth > 0:
            dish_cutters.append(box_centered(
                clip_len,
                gap,
                groove_depth + 0.08,
                groove_z,
                cx,
                slot_y,
            ))

        # Two vertical side walls. Together with the dish top/groove, they form
        # the U-shaped acrylic clip. These are fused into the dish body.
        solids.append(box_centered(clip_len, wall, wall_h, wall_z, cx, inner_wall_y))
        solids.append(box_centered(clip_len, wall, wall_h, wall_z, cx, outer_wall_y))

    return dish_cutters, solids


def make_dish():
    """v36 dish: v33 dish plus two short fused U-clips on one long side."""
    shape = _make_dish_v33()
    if not simple_acrylic_u_clips_enabled():
        return shape

    x, y = opening_centres()[simple_acrylic_u_clip_opening_index() - 1]
    dish_cutters, solids = simple_acrylic_u_clip_shapes_for_opening(x, y)

    if dish_cutters:
        shape = cut_many(shape, dish_cutters)
    if solids:
        shape = fuse_many([shape] + solids)
    return safe_fillet(shape, P.fillet_radius)


def validate_parameters():
    _validate_parameters_v33()
    if not simple_acrylic_u_clips_enabled():
        return

    sheet_t = max(0.10, float(getattr(P, "acrylic_sheet_thickness", 2.0)))
    if simple_acrylic_u_inner_gap() < sheet_t - 1e-6:
        raise ValueError(
            "simple_acrylic_u_clip_inner_gap is smaller than acrylic_sheet_thickness. "
            "Use about 2.1-2.2 mm for a 2.0 mm acrylic sheet."
        )
    if simple_acrylic_u_base_groove_depth() >= float(P.dish_thickness) - 0.05:
        raise ValueError("simple_acrylic_u_clip_base_groove_depth must be smaller than dish_thickness.")

    seat_l = simple_acrylic_u_seat_length()
    seat_w = simple_acrylic_u_seat_width()
    clip_len = simple_acrylic_u_clip_length()
    offset = simple_acrylic_u_clip_offset_from_center(seat_l)
    if simple_acrylic_u_clip_count() == 2 and (offset + clip_len / 2.0 > seat_l / 2.0 + 0.5):
        raise ValueError(
            "The two acrylic U-clips extend too far along the selected long side. "
            "Reduce simple_acrylic_u_clip_length or simple_acrylic_u_clip_offset_from_center."
        )

    x, y = opening_centres()[simple_acrylic_u_clip_opening_index() - 1]
    sign = _simple_acrylic_long_side_sign(y)
    wall = simple_acrylic_u_wall_thickness()
    gap = simple_acrylic_u_inner_gap()
    clearance = simple_acrylic_u_clearance_from_basket_recess()
    outer_y = y + sign * (seat_w / 2.0 + clearance + 2.0 * wall + gap)
    clip_x_extent = abs(x) + max(abs(offset) + clip_len / 2.0, clip_len / 2.0)

    if clip_x_extent > effective_dish_outer_length() / 2.0 + 1e-6:
        raise ValueError("Simple acrylic U-clips exceed dish length; reduce offset/length or increase dish size.")
    if abs(outer_y) > effective_dish_outer_width() / 2.0 + 1e-6:
        raise ValueError("Simple acrylic U-clips exceed dish width; reduce wall/gap/clearance or increase dish size.")


def create_document():
    """v36: show only the dish, with fused U-clips."""
    validate_parameters()
    doc = App.newDocument("PET_Plant_Dish_Only_V36")
    dish_shape = make_dish()
    add_feature(doc, "Dish_Only_With_Two_Acrylic_U_Clips", dish_shape,
                color=(0.35, 0.55, 0.95), transparency=20)

    App.Console.PrintMessage("Created dish-only v36 with two fused acrylic U-clips on one long side of one opening.\n")
    App.Console.PrintMessage(
        f"U-clip opening index: {simple_acrylic_u_clip_opening_index()}, "
        f"side: {simple_acrylic_u_clip_side()}, count: {simple_acrylic_u_clip_count()}\n"
    )
    App.Console.PrintMessage(
        f"U-clip length: {simple_acrylic_u_clip_length():.2f} mm; "
        f"inner gap: {simple_acrylic_u_inner_gap():.2f} mm; "
        f"height: {simple_acrylic_u_height():.2f} mm\n"
    )

    doc.recompute()
    if Gui is not None:
        Gui.ActiveDocument.ActiveView.viewAxonometric()
        Gui.SendMsgToActiveView("ViewFit")
    maybe_export(doc)
    return doc



# -----------------------------------------------------------------------------
# Revision v37 overrides — bolt holes through each simple acrylic U-clip
# -----------------------------------------------------------------------------
# Adds one horizontal through-hole per U-clip. The hole runs across the U gap,
# passing through the inner wall, the acrylic-sheet gap, and the outer wall, so a
# small screw/bolt can clamp the acrylic sheet. The U-clips remain fused to the
# dish and the document still shows only the dish.

_validate_parameters_v36 = validate_parameters


def simple_acrylic_u_bolt_holes_enabled():
    return bool(getattr(P, "simple_acrylic_u_clip_add_bolt_holes", True))


def simple_acrylic_u_bolt_hole_diameter():
    return max(0.20, float(getattr(P, "simple_acrylic_u_clip_bolt_hole_diameter", 2.4)))


def simple_acrylic_u_bolt_hole_height_above_dish():
    return max(0.0, float(getattr(P, "simple_acrylic_u_clip_bolt_hole_height_above_dish", 7.0)))


def simple_acrylic_u_bolt_hole_x_offset():
    return float(getattr(P, "simple_acrylic_u_clip_bolt_hole_x_offset", 0.0))


def simple_acrylic_u_bolt_hole_extra_length():
    return max(0.0, float(getattr(P, "simple_acrylic_u_clip_bolt_hole_extra_length", 2.0)))


def simple_acrylic_u_clip_shapes_for_opening_v37(x, y):
    """Return (dish_cutters, solids, bolt_hole_cutters) for the simple U-clips.

    The two raised walls form the U. The bolt hole cutter is a horizontal
    cylinder along Y, centred across the full U width, so it cuts both walls and
    crosses the acrylic gap.
    """
    seat_l = simple_acrylic_u_seat_length()
    seat_w = simple_acrylic_u_seat_width()
    sign = _simple_acrylic_long_side_sign(y)

    clip_count = simple_acrylic_u_clip_count()
    clip_len = simple_acrylic_u_clip_length()
    offset = simple_acrylic_u_clip_offset_from_center(seat_l)
    gap = simple_acrylic_u_inner_gap()
    wall = simple_acrylic_u_wall_thickness()
    height = simple_acrylic_u_height()
    clearance = simple_acrylic_u_clearance_from_basket_recess()
    groove_depth = simple_acrylic_u_base_groove_depth()

    z_top = float(P.dish_thickness)
    base_overlap = min(0.20, height * 0.15)
    wall_z = z_top - base_overlap
    wall_h = height + base_overlap
    groove_z = z_top - groove_depth

    # One long side of the basket-lip recess.
    edge_y = y + sign * seat_w / 2.0
    inner_wall_y = edge_y + sign * (clearance + wall / 2.0)
    slot_y = edge_y + sign * (clearance + wall + gap / 2.0)
    outer_wall_y = edge_y + sign * (clearance + wall + gap + wall / 2.0)

    if clip_count == 1:
        centres_x = [x]
    elif clip_count == 2:
        centres_x = [x - offset, x + offset]
    else:
        usable = max(0.0, seat_l - clip_len)
        span = min(usable, 2.0 * offset)
        centres_x = [x - span / 2.0 + i * span / float(clip_count - 1) for i in range(clip_count)]

    dish_cutters = []
    solids = []
    bolt_cutters = []

    bolt_z = z_top + simple_acrylic_u_bolt_hole_height_above_dish()
    bolt_d = simple_acrylic_u_bolt_hole_diameter()
    bolt_x_offset = simple_acrylic_u_bolt_hole_x_offset()
    # Long enough to pass through both U walls and the empty acrylic gap.
    bolt_len = 2.0 * wall + gap + 2.0 * simple_acrylic_u_bolt_hole_extra_length()

    for cx in centres_x:
        if groove_depth > 0:
            dish_cutters.append(box_centered(
                clip_len,
                gap,
                groove_depth + 0.08,
                groove_z,
                cx,
                slot_y,
            ))

        # Two vertical side walls fused into the dish body.
        solids.append(box_centered(clip_len, wall, wall_h, wall_z, cx, inner_wall_y))
        solids.append(box_centered(clip_len, wall, wall_h, wall_z, cx, outer_wall_y))

        if simple_acrylic_u_bolt_holes_enabled():
            # One through-hole per U-clip. Axis is along Y, crossing the two U
            # walls and the acrylic-sheet gap.
            bolt_cutters.append(cylinder_y(
                bolt_d,
                bolt_len,
                bolt_z,
                cx + bolt_x_offset,
                slot_y,
            ))

    return dish_cutters, solids, bolt_cutters


def make_dish():
    """v37 dish: v33 dish plus two short fused U-clips with one bolt hole each."""
    shape = _make_dish_v33()
    if not simple_acrylic_u_clips_enabled():
        return shape

    x, y = opening_centres()[simple_acrylic_u_clip_opening_index() - 1]
    dish_cutters, solids, bolt_cutters = simple_acrylic_u_clip_shapes_for_opening_v37(x, y)

    if dish_cutters:
        shape = cut_many(shape, dish_cutters)
    if solids:
        shape = fuse_many([shape] + solids)
    if bolt_cutters:
        # Cut after fusing the U walls so the holes pass through the final fused body.
        shape = cut_many(shape, bolt_cutters)
    return safe_fillet(shape, P.fillet_radius)


def validate_parameters():
    _validate_parameters_v36()
    if not (simple_acrylic_u_clips_enabled() and simple_acrylic_u_bolt_holes_enabled()):
        return

    d = simple_acrylic_u_bolt_hole_diameter()
    h = simple_acrylic_u_height()
    z = simple_acrylic_u_bolt_hole_height_above_dish()
    clip_len = simple_acrylic_u_clip_length()
    x_off = abs(simple_acrylic_u_bolt_hole_x_offset())

    if d >= h - 0.4:
        raise ValueError("simple_acrylic_u_clip_bolt_hole_diameter is too large for the U-clip height.")
    if z - d / 2.0 < 0.25:
        raise ValueError("Bolt hole is too low; increase simple_acrylic_u_clip_bolt_hole_height_above_dish.")
    if z + d / 2.0 > h + 0.25:
        raise ValueError("Bolt hole is too high; reduce simple_acrylic_u_clip_bolt_hole_height_above_dish or increase U-clip height.")
    if x_off + d / 2.0 > clip_len / 2.0 - 0.25:
        raise ValueError("Bolt hole x-offset places the hole too close to the end of the 10 mm U-clip.")


def create_document():
    """v37: show only the dish, with fused U-clips and bolt holes."""
    validate_parameters()
    doc = App.newDocument("PET_Plant_Dish_Only_V37")
    dish_shape = make_dish()
    add_feature(doc, "Dish_Only_With_Two_Acrylic_U_Clips_And_Bolt_Holes", dish_shape,
                color=(0.35, 0.55, 0.95), transparency=20)

    App.Console.PrintMessage("Created dish-only v37 with two fused acrylic U-clips and one bolt hole through each U.\n")
    App.Console.PrintMessage(
        f"U-clip opening index: {simple_acrylic_u_clip_opening_index()}, "
        f"side: {simple_acrylic_u_clip_side()}, count: {simple_acrylic_u_clip_count()}\n"
    )
    App.Console.PrintMessage(
        f"U-clip length: {simple_acrylic_u_clip_length():.2f} mm; "
        f"inner gap: {simple_acrylic_u_inner_gap():.2f} mm; "
        f"height: {simple_acrylic_u_height():.2f} mm\n"
    )
    if simple_acrylic_u_bolt_holes_enabled():
        App.Console.PrintMessage(
            f"Bolt hole diameter: {simple_acrylic_u_bolt_hole_diameter():.2f} mm; "
            f"height above dish: {simple_acrylic_u_bolt_hole_height_above_dish():.2f} mm\n"
        )

    doc.recompute()
    if Gui is not None:
        Gui.ActiveDocument.ActiveView.viewAxonometric()
        Gui.SendMsgToActiveView("ViewFit")
    maybe_export(doc)
    return doc


# -----------------------------------------------------------------------------
# Revision v38 overrides — symmetric U-clips around all selected dish openings
# -----------------------------------------------------------------------------
# Places the same 10 mm U-clips from v37 at symmetric positions around the four
# basket openings, matching the user's red-rectangle sketch. The U-clips are
# fused into the dish body, and each U can keep the v37 bolt/screw hole.
# Only the dish is shown in the document.

# Force older acrylic trials off so only the v38 symmetric layout is generated.
P.enable_acrylic_u_channels = False
P.enable_acrylic_window_guides = False
P.enable_simple_acrylic_u_clips = False
P.show_acrylic_u_sheet_preview = False
P.show_acrylic_window_sheet_preview = False


def symmetric_acrylic_u_clips_enabled():
    return bool(getattr(P, "enable_symmetric_acrylic_u_clips", True))


def symmetric_acrylic_u_clip_indices():
    raw = getattr(P, "symmetric_acrylic_u_clip_opening_indices", (1, 2, 3, 4))
    if isinstance(raw, int):
        raw = (raw,)
    if isinstance(raw, str):
        raw = raw.replace(",", " ").split()
    out = []
    for item in raw:
        try:
            idx = int(item)
        except Exception:
            continue
        if 1 <= idx <= 4 and idx not in out:
            out.append(idx)
    return out or [1, 2, 3, 4]


def symmetric_acrylic_u_clip_sides():
    raw = getattr(P, "symmetric_acrylic_u_clip_sides", ("N", "S", "E", "W"))
    if isinstance(raw, str):
        key = raw.strip().lower()
        if key in {"all", "all_sides", "around", "perimeter"}:
            return ["N", "S", "E", "W"]
        if key in {"long", "long_sides", "horizontal"}:
            return ["N", "S"]
        if key in {"short", "short_sides", "vertical"}:
            return ["E", "W"]
        raw = raw.replace(",", " ").split()
    out = []
    mapping = {
        "N": "N", "NORTH": "N", "+Y": "N", "TOP": "N", "UPPER": "N",
        "S": "S", "SOUTH": "S", "-Y": "S", "BOTTOM": "S", "LOWER": "S",
        "E": "E", "EAST": "E", "+X": "E", "RIGHT": "E",
        "W": "W", "WEST": "W", "-X": "W", "LEFT": "W",
    }
    for item in raw:
        side = mapping.get(str(item).strip().upper())
        if side and side not in out:
            out.append(side)
    return out or ["N", "S", "E", "W"]


def symmetric_u_count_for_side(side):
    side = str(side).upper()
    if side in {"N", "S"}:
        return max(1, int(getattr(P, "symmetric_acrylic_u_clip_count_long_side", 2)))
    return max(1, int(getattr(P, "symmetric_acrylic_u_clip_count_short_side", 2)))


def symmetric_u_manual_offset_for_side(side):
    side = str(side).upper()
    if side in {"N", "S"}:
        return max(0.0, float(getattr(P, "symmetric_acrylic_u_clip_long_side_offset_from_center", 0.0)))
    return max(0.0, float(getattr(P, "symmetric_acrylic_u_clip_short_side_offset_from_center", 0.0)))


def _symmetric_u_axis_centres(axis_center, span, count, clip_len, manual_offset):
    axis_center = float(axis_center)
    span = float(span)
    count = max(1, int(count))
    clip_len = float(clip_len)
    manual_offset = float(manual_offset)
    if count == 1:
        return [axis_center]
    if count == 2:
        offset = manual_offset if manual_offset > 0 else max(0.0, span * 0.25)
        return [axis_center - offset, axis_center + offset]

    # For 3 or more clips, distribute symmetrically within the side span while
    # keeping clip ends inside the basket-seat/recess footprint.
    usable_span = max(0.0, span - clip_len)
    if usable_span <= 1e-6:
        return [axis_center]
    return [axis_center - usable_span / 2.0 + i * usable_span / float(count - 1)
            for i in range(count)]


def _u_wall_and_bolt_common():
    gap = simple_acrylic_u_inner_gap()
    wall = simple_acrylic_u_wall_thickness()
    height = simple_acrylic_u_height()
    clearance = simple_acrylic_u_clearance_from_basket_recess()
    groove_depth = simple_acrylic_u_base_groove_depth()
    clip_len = simple_acrylic_u_clip_length()
    z_top = float(P.dish_thickness)
    base_overlap = min(0.20, height * 0.15)
    wall_z = z_top - base_overlap
    wall_h = height + base_overlap
    groove_z = z_top - groove_depth
    bolt_z = z_top + simple_acrylic_u_bolt_hole_height_above_dish()
    bolt_d = simple_acrylic_u_bolt_hole_diameter()
    bolt_len = 2.0 * wall + gap + 2.0 * simple_acrylic_u_bolt_hole_extra_length()
    bolt_axis_offset = simple_acrylic_u_bolt_hole_x_offset()
    return {
        "gap": gap,
        "wall": wall,
        "height": height,
        "clearance": clearance,
        "groove_depth": groove_depth,
        "clip_len": clip_len,
        "z_top": z_top,
        "wall_z": wall_z,
        "wall_h": wall_h,
        "groove_z": groove_z,
        "bolt_z": bolt_z,
        "bolt_d": bolt_d,
        "bolt_len": bolt_len,
        "bolt_axis_offset": bolt_axis_offset,
    }


def symmetric_acrylic_u_clip_shapes_for_side(x, y, side):
    """Return (dish_cutters, solids, bolt_cutters) for one side of one opening.

    N/S sides run along X and hold an acrylic sheet whose thickness is in Y.
    E/W sides run along Y and hold an acrylic sheet whose thickness is in X.
    """
    side = str(side).strip().upper()
    seat_l = simple_acrylic_u_seat_length()
    seat_w = simple_acrylic_u_seat_width()
    p = _u_wall_and_bolt_common()
    clip_len = p["clip_len"]
    gap = p["gap"]
    wall = p["wall"]
    clearance = p["clearance"]
    groove_depth = p["groove_depth"]

    dish_cutters = []
    solids = []
    bolt_cutters = []

    if side in {"N", "S"}:
        sign = 1.0 if side == "N" else -1.0
        centres = _symmetric_u_axis_centres(
            x,
            seat_l,
            symmetric_u_count_for_side(side),
            clip_len,
            symmetric_u_manual_offset_for_side(side),
        )
        edge_y = y + sign * seat_w / 2.0
        inner_wall_y = edge_y + sign * (clearance + wall / 2.0)
        slot_y = edge_y + sign * (clearance + wall + gap / 2.0)
        outer_wall_y = edge_y + sign * (clearance + wall + gap + wall / 2.0)

        for cx in centres:
            if groove_depth > 0:
                dish_cutters.append(box_centered(
                    clip_len, gap, groove_depth + 0.08, p["groove_z"], cx, slot_y
                ))
            solids.append(box_centered(clip_len, wall, p["wall_h"], p["wall_z"], cx, inner_wall_y))
            solids.append(box_centered(clip_len, wall, p["wall_h"], p["wall_z"], cx, outer_wall_y))
            if simple_acrylic_u_bolt_holes_enabled():
                bolt_cutters.append(cylinder_y(
                    p["bolt_d"], p["bolt_len"], p["bolt_z"],
                    cx + p["bolt_axis_offset"], slot_y
                ))
        return dish_cutters, solids, bolt_cutters

    if side in {"E", "W"}:
        sign = 1.0 if side == "E" else -1.0
        centres = _symmetric_u_axis_centres(
            y,
            seat_w,
            symmetric_u_count_for_side(side),
            clip_len,
            symmetric_u_manual_offset_for_side(side),
        )
        edge_x = x + sign * seat_l / 2.0
        inner_wall_x = edge_x + sign * (clearance + wall / 2.0)
        slot_x = edge_x + sign * (clearance + wall + gap / 2.0)
        outer_wall_x = edge_x + sign * (clearance + wall + gap + wall / 2.0)

        for cy in centres:
            if groove_depth > 0:
                dish_cutters.append(box_centered(
                    gap, clip_len, groove_depth + 0.08, p["groove_z"], slot_x, cy
                ))
            solids.append(box_centered(wall, clip_len, p["wall_h"], p["wall_z"], inner_wall_x, cy))
            solids.append(box_centered(wall, clip_len, p["wall_h"], p["wall_z"], outer_wall_x, cy))
            if simple_acrylic_u_bolt_holes_enabled():
                # For vertical-side clips, the same offset parameter moves the
                # hole along the clip length, i.e. in Y.
                bolt_cutters.append(cylinder_x(
                    p["bolt_d"], p["bolt_len"], p["bolt_z"],
                    slot_x, cy + p["bolt_axis_offset"]
                ))
        return dish_cutters, solids, bolt_cutters

    return dish_cutters, solids, bolt_cutters


def symmetric_acrylic_u_clip_all_shapes():
    dish_cutters = []
    solids = []
    bolt_cutters = []
    centres = opening_centres()
    sides = symmetric_acrylic_u_clip_sides()
    for idx in symmetric_acrylic_u_clip_indices():
        x, y = centres[idx - 1]
        for side in sides:
            c, s, b = symmetric_acrylic_u_clip_shapes_for_side(x, y, side)
            dish_cutters.extend(c)
            solids.extend(s)
            bolt_cutters.extend(b)
    return dish_cutters, solids, bolt_cutters


def make_dish():
    """v38 dish: v33 dish plus symmetric fused U-clips and bolt holes."""
    shape = _make_dish_v33()
    if not symmetric_acrylic_u_clips_enabled():
        return shape

    dish_cutters, solids, bolt_cutters = symmetric_acrylic_u_clip_all_shapes()
    if dish_cutters:
        shape = cut_many(shape, dish_cutters)
    if solids:
        shape = fuse_many([shape] + solids)
    if bolt_cutters:
        shape = cut_many(shape, bolt_cutters)
    return safe_fillet(shape, P.fillet_radius)


def validate_parameters():
    _validate_parameters_v33()
    if not symmetric_acrylic_u_clips_enabled():
        return

    sheet_t = max(0.10, float(getattr(P, "acrylic_sheet_thickness", 2.0)))
    if simple_acrylic_u_inner_gap() < sheet_t - 1e-6:
        raise ValueError(
            "simple_acrylic_u_clip_inner_gap is smaller than acrylic_sheet_thickness. "
            "Use about 2.1-2.2 mm for a 2.0 mm acrylic sheet."
        )
    if simple_acrylic_u_base_groove_depth() >= float(P.dish_thickness) - 0.05:
        raise ValueError("simple_acrylic_u_clip_base_groove_depth must be smaller than dish_thickness.")

    # Keep bolt holes inside the upright U walls.
    if simple_acrylic_u_bolt_holes_enabled():
        d = simple_acrylic_u_bolt_hole_diameter()
        h = simple_acrylic_u_height()
        z = simple_acrylic_u_bolt_hole_height_above_dish()
        clip_len = simple_acrylic_u_clip_length()
        axis_off = abs(simple_acrylic_u_bolt_hole_x_offset())
        if d >= h - 0.4:
            raise ValueError("simple_acrylic_u_clip_bolt_hole_diameter is too large for the U-clip height.")
        if z - d / 2.0 < 0.25:
            raise ValueError("Bolt hole is too low; increase simple_acrylic_u_clip_bolt_hole_height_above_dish.")
        if z + d / 2.0 > h + 0.25:
            raise ValueError("Bolt hole is too high; reduce simple_acrylic_u_clip_bolt_hole_height_above_dish or increase U-clip height.")
        if axis_off + d / 2.0 > clip_len / 2.0 - 0.25:
            raise ValueError("Bolt-hole offset places the hole too close to the end of the 10 mm U-clip.")

    # Conservative footprint check: all U walls must stay inside the dish plate.
    dish_half_l = effective_dish_outer_length() / 2.0
    dish_half_w = effective_dish_outer_width() / 2.0
    seat_l = simple_acrylic_u_seat_length()
    seat_w = simple_acrylic_u_seat_width()
    clip_len = simple_acrylic_u_clip_length()
    wall = simple_acrylic_u_wall_thickness()
    gap = simple_acrylic_u_inner_gap()
    clearance = simple_acrylic_u_clearance_from_basket_recess()
    radial_out = clearance + 2.0 * wall + gap

    for idx in symmetric_acrylic_u_clip_indices():
        x, y = opening_centres()[idx - 1]
        for side in symmetric_acrylic_u_clip_sides():
            side = side.upper()
            count = symmetric_u_count_for_side(side)
            manual_offset = symmetric_u_manual_offset_for_side(side)
            if side in {"N", "S"}:
                centres_axis = _symmetric_u_axis_centres(x, seat_l, count, clip_len, manual_offset)
                x_extent = max(abs(cx) + clip_len / 2.0 for cx in centres_axis)
                y_edge = y + (1.0 if side == "N" else -1.0) * (seat_w / 2.0 + radial_out)
                if x_extent > dish_half_l + 1e-6:
                    raise ValueError(f"Symmetric U-clips on opening {idx} exceed dish length.")
                if abs(y_edge) > dish_half_w + 1e-6:
                    raise ValueError(f"Symmetric U-clips on opening {idx} exceed dish width.")
            else:
                centres_axis = _symmetric_u_axis_centres(y, seat_w, count, clip_len, manual_offset)
                y_extent = max(abs(cy) + clip_len / 2.0 for cy in centres_axis)
                x_edge = x + (1.0 if side == "E" else -1.0) * (seat_l / 2.0 + radial_out)
                if abs(x_edge) > dish_half_l + 1e-6:
                    raise ValueError(f"Symmetric U-clips on opening {idx} exceed dish length.")
                if y_extent > dish_half_w + 1e-6:
                    raise ValueError(f"Symmetric U-clips on opening {idx} exceed dish width.")


def create_document():
    """v38: show only the dish, with all symmetric fused U-clips and bolt holes."""
    validate_parameters()
    doc = App.newDocument("PET_Plant_Dish_Only_V38")
    dish_shape = make_dish()
    add_feature(doc, "Dish_Only_With_Symmetric_Acrylic_U_Clips", dish_shape,
                color=(0.35, 0.55, 0.95), transparency=20)

    App.Console.PrintMessage("Created dish-only v38 with symmetric fused acrylic U-clips around selected openings.\n")
    App.Console.PrintMessage(
        f"Openings: {symmetric_acrylic_u_clip_indices()}; sides: {symmetric_acrylic_u_clip_sides()}\n"
    )
    App.Console.PrintMessage(
        f"U-clip length: {simple_acrylic_u_clip_length():.2f} mm; "
        f"inner gap: {simple_acrylic_u_inner_gap():.2f} mm; "
        f"wall: {simple_acrylic_u_wall_thickness():.2f} mm; "
        f"height: {simple_acrylic_u_height():.2f} mm\n"
    )
    if simple_acrylic_u_bolt_holes_enabled():
        App.Console.PrintMessage(
            f"Bolt hole diameter: {simple_acrylic_u_bolt_hole_diameter():.2f} mm; "
            f"height above dish: {simple_acrylic_u_bolt_hole_height_above_dish():.2f} mm\n"
        )

    doc.recompute()
    if Gui is not None:
        Gui.ActiveDocument.ActiveView.viewAxonometric()
        Gui.SendMsgToActiveView("ViewFit")
    maybe_export(doc)
    return doc


# -----------------------------------------------------------------------------
# Revision v39 overrides — share U-clips in the internal strips between openings
# -----------------------------------------------------------------------------
# Correction to v38:
#   - External sides still use the requested symmetric U clips.
#   - Where two neighbouring dish openings share the same central strip/rib,
#     only ONE shared pair of U clips is generated in that strip.
#   - This avoids the crowded four-clip duplication between openings.
#   - The shared U clips use the same dimensions and bolt-hole parameters.
#   - Only the dish is shown.

# Keep this visible/overridable even if the pasted parameter block did not include it.
if not hasattr(P, "symmetric_acrylic_u_clip_share_internal_sides"):
    P.symmetric_acrylic_u_clip_share_internal_sides = True
if not hasattr(P, "symmetric_acrylic_u_clip_internal_side_count"):
    P.symmetric_acrylic_u_clip_internal_side_count = 2


def symmetric_acrylic_u_clip_share_internal_sides():
    return bool(getattr(P, "symmetric_acrylic_u_clip_share_internal_sides", True))


def symmetric_acrylic_u_clip_internal_side_count():
    return max(1, int(getattr(P, "symmetric_acrylic_u_clip_internal_side_count", 2)))


# Neighbour map for the 2 x 2 dish opening order:
#   3  4
#   1  2
_INTERNAL_NEIGHBOUR_FOR_SIDE = {
    (1, "E"): 2, (2, "W"): 1,
    (3, "E"): 4, (4, "W"): 3,
    (1, "N"): 3, (3, "S"): 1,
    (2, "N"): 4, (4, "S"): 2,
}


def _symmetric_shared_u_axis_centres(axis_center, span, orientation):
    """Centres for the two shared U clips between neighbouring openings."""
    orientation = str(orientation).upper()
    manual = symmetric_u_manual_offset_for_side("N" if orientation == "X" else "E")
    return _symmetric_u_axis_centres(
        axis_center,
        span,
        symmetric_acrylic_u_clip_internal_side_count(),
        simple_acrylic_u_clip_length(),
        manual,
    )


def symmetric_acrylic_u_clip_shapes_for_shared_line(x_center, y_center, orientation):
    """Return (dish_cutters, solids, bolt_cutters) for a shared internal strip.

    orientation="X" means the clip length runs along X, with acrylic thickness in Y.
    orientation="Y" means the clip length runs along Y, with acrylic thickness in X.
    The U channel is centred on the middle of the strip between two adjacent openings.
    """
    orientation = str(orientation).strip().upper()
    p = _u_wall_and_bolt_common()
    clip_len = p["clip_len"]
    gap = p["gap"]
    wall = p["wall"]
    groove_depth = p["groove_depth"]

    dish_cutters = []
    solids = []
    bolt_cutters = []

    if orientation == "X":
        # Shared strip between lower/upper openings. Clips run along X.
        centres = _symmetric_shared_u_axis_centres(x_center, simple_acrylic_u_seat_length(), "X")
        wall_offset = gap / 2.0 + wall / 2.0
        wall_y_a = y_center - wall_offset
        wall_y_b = y_center + wall_offset
        slot_y = y_center

        for cx in centres:
            if groove_depth > 0:
                dish_cutters.append(box_centered(
                    clip_len, gap, groove_depth + 0.08, p["groove_z"], cx, slot_y
                ))
            solids.append(box_centered(clip_len, wall, p["wall_h"], p["wall_z"], cx, wall_y_a))
            solids.append(box_centered(clip_len, wall, p["wall_h"], p["wall_z"], cx, wall_y_b))
            if simple_acrylic_u_bolt_holes_enabled():
                bolt_cutters.append(cylinder_y(
                    p["bolt_d"], p["bolt_len"], p["bolt_z"],
                    cx + p["bolt_axis_offset"], slot_y
                ))
        return dish_cutters, solids, bolt_cutters

    if orientation == "Y":
        # Shared strip between left/right openings. Clips run along Y.
        centres = _symmetric_shared_u_axis_centres(y_center, simple_acrylic_u_seat_width(), "Y")
        wall_offset = gap / 2.0 + wall / 2.0
        wall_x_a = x_center - wall_offset
        wall_x_b = x_center + wall_offset
        slot_x = x_center

        for cy in centres:
            if groove_depth > 0:
                dish_cutters.append(box_centered(
                    gap, clip_len, groove_depth + 0.08, p["groove_z"], slot_x, cy
                ))
            solids.append(box_centered(wall, clip_len, p["wall_h"], p["wall_z"], wall_x_a, cy))
            solids.append(box_centered(wall, clip_len, p["wall_h"], p["wall_z"], wall_x_b, cy))
            if simple_acrylic_u_bolt_holes_enabled():
                bolt_cutters.append(cylinder_x(
                    p["bolt_d"], p["bolt_len"], p["bolt_z"],
                    slot_x, cy + p["bolt_axis_offset"]
                ))
        return dish_cutters, solids, bolt_cutters

    return dish_cutters, solids, bolt_cutters


def _add_shared_internal_u_clip_pair(idx, neighbour, centres, dish_cutters, solids, bolt_cutters):
    """Add one shared U-clip pair between two adjacent openings."""
    x1, y1 = centres[idx - 1]
    x2, y2 = centres[neighbour - 1]
    x_mid = (x1 + x2) / 2.0
    y_mid = (y1 + y2) / 2.0

    # Different X -> left/right neighbours; shared line runs along Y.
    if abs(x1 - x2) > abs(y1 - y2):
        c, s, b = symmetric_acrylic_u_clip_shapes_for_shared_line(x_mid, y_mid, "Y")
    else:
        # Different Y -> lower/upper neighbours; shared line runs along X.
        c, s, b = symmetric_acrylic_u_clip_shapes_for_shared_line(x_mid, y_mid, "X")

    dish_cutters.extend(c)
    solids.extend(s)
    bolt_cutters.extend(b)


def symmetric_acrylic_u_clip_all_shapes():
    """v39: generate external sides normally but internal shared strips only once."""
    dish_cutters = []
    solids = []
    bolt_cutters = []
    centres = opening_centres()
    selected = set(symmetric_acrylic_u_clip_indices())
    sides = symmetric_acrylic_u_clip_sides()
    seen_shared_pairs = set()

    for idx in symmetric_acrylic_u_clip_indices():
        x, y = centres[idx - 1]
        for side in sides:
            side = str(side).upper()
            neighbour = _INTERNAL_NEIGHBOUR_FOR_SIDE.get((idx, side))

            if (symmetric_acrylic_u_clip_share_internal_sides()
                    and neighbour in selected):
                pair_key = tuple(sorted((idx, neighbour)))
                if pair_key not in seen_shared_pairs:
                    seen_shared_pairs.add(pair_key)
                    _add_shared_internal_u_clip_pair(idx, neighbour, centres,
                                                     dish_cutters, solids, bolt_cutters)
                # Do not also add the duplicate opening-specific side.
                continue

            # Outside/perimeter side, or no matching selected neighbour.
            c, s, b = symmetric_acrylic_u_clip_shapes_for_side(x, y, side)
            dish_cutters.extend(c)
            solids.extend(s)
            bolt_cutters.extend(b)

    return dish_cutters, solids, bolt_cutters


# Reuse the v38 geometry builder; it calls symmetric_acrylic_u_clip_all_shapes(),
# which is now overridden above.
_make_dish_v39_base = make_dish
_validate_parameters_v38 = validate_parameters


def validate_parameters():
    """v39 validation: same dimensional checks, with shared internal clips enabled."""
    # The v38 validation checks the U dimensions, bolt holes, and outer footprint.
    # It may be slightly conservative because v39 removes duplicate internal clips,
    # which is safe for this layout.
    _validate_parameters_v38()


def create_document():
    """v39: show only the dish, with shared internal U-clip pairs."""
    validate_parameters()
    doc = App.newDocument("PET_Plant_Dish_Only_V39")
    dish_shape = make_dish()
    add_feature(doc, "Dish_Only_With_Shared_Internal_Acrylic_U_Clips", dish_shape,
                color=(0.35, 0.55, 0.95), transparency=20)

    App.Console.PrintMessage("Created dish-only v39 with shared internal acrylic U-clips.\n")
    App.Console.PrintMessage(
        f"Openings: {symmetric_acrylic_u_clip_indices()}; sides: {symmetric_acrylic_u_clip_sides()}\n"
    )
    App.Console.PrintMessage(
        f"Internal strips shared: {symmetric_acrylic_u_clip_share_internal_sides()}; "
        f"clips per internal strip: {symmetric_acrylic_u_clip_internal_side_count()}\n"
    )
    App.Console.PrintMessage(
        f"U-clip length: {simple_acrylic_u_clip_length():.2f} mm; "
        f"inner gap: {simple_acrylic_u_inner_gap():.2f} mm; "
        f"wall: {simple_acrylic_u_wall_thickness():.2f} mm; "
        f"height: {simple_acrylic_u_height():.2f} mm\n"
    )
    if simple_acrylic_u_bolt_holes_enabled():
        App.Console.PrintMessage(
            f"Bolt hole diameter: {simple_acrylic_u_bolt_hole_diameter():.2f} mm; "
            f"height above dish: {simple_acrylic_u_bolt_hole_height_above_dish():.2f} mm\n"
        )

    doc.recompute()
    if Gui is not None:
        Gui.ActiveDocument.ActiveView.viewAxonometric()
        Gui.SendMsgToActiveView("ViewFit")
    maybe_export(doc)
    return doc


if __name__ == "__main__":
    create_document()
